"""
StandaloneCoPilot - Manufacturing Co-Pilot with Standalone Implementation
A FreeCAD macro that provides AI-powered manufacturing intelligence
with enhanced UI and cloud backend integration.

This version is completely standalone and doesn't rely on the existing modules,
implementing a strict singleton pattern to prevent multiple instances.
Cloud features (DFM, cost estimation, tool recommendations) are offloaded
to cloud services for lightweight operation.

Author: Samarjit
License: MIT
Version: 1.1.0 - Cloud Integration for DFM, Cost, and Tool Features
"""

import os
import FreeCAD
import FreeCADGui
import json
import os
import sys
import traceback
import time
import math
import threading
from datetime import datetime
import Mesh, MeshPart
from collections import defaultdict
from math import inf
import urllib.request
import urllib.parse
from typing import Dict, List, Any, Optional, Tuple, Union, Callable
from datetime import datetime
from PySide2 import QtWidgets, QtCore, QtGui
from PySide2.QtWidgets import QApplication

# Try to import FreeCAD modules
try:
    import FreeCAD
    import Part
    import FreeCADGui
except ImportError:
    print("Error: Required modules not found. This macro requires PySide2 and FreeCAD.")
    raise

# Global singleton instance tracker
_STANDALONE_INSTANCE = None

# Add cloud services directory to path
_THIS_DIR = os.path.dirname(os.path.abspath(__file__))
if _THIS_DIR not in sys.path:
    sys.path.append(_THIS_DIR)

# Try to import TextToCADIntegration
try:
    from text_to_cad_integration import TextToCADIntegration
    _TEXT_TO_CAD_AVAILABLE = True
except ImportError:
    print("Warning: TextToCADIntegration not available")
    _TEXT_TO_CAD_AVAILABLE = False

# Try to import Anthropic for Claude integration
try:
    import anthropic
    _ANTHROPIC_AVAILABLE = True
except ImportError:
    print("Warning: Anthropic library not available for Claude integration")
    _ANTHROPIC_AVAILABLE = False

# Environment variable loading for Claude
def load_anthropic_api_key():
    """Load Anthropic API key from environment or .env file"""
    # Try environment variable first
    api_key = os.environ.get('ANTHROPIC_API_KEY')
    if api_key:
        return api_key
    
    # Try .env file
    try:
        env_file = os.path.join(_THIS_DIR, '.env')
        if os.path.exists(env_file):
            with open(env_file, 'r') as f:
                for line in f:
                    if line.startswith('ANTHROPIC_API_KEY='):
                        return line.split('=', 1)[1].strip().strip('"\'')
    except Exception as e:
        print(f"Warning: Could not load .env file: {e}")
    
    return None

# ========== PROFESSIONAL DFM OVERLAY/TOOLTIP SYSTEM ==========
# Professional DFM overlay system with per-issue mesh overlays and 3D view tooltips

# ---------- STYLE ----------
SEVERITY_STYLE = {
    "critical": {"color": (1.0, 0.0, 0.0),   "transparency": 35},  # #FF0000
    "high":     {"color": (1.0, 0.302, 0.0), "transparency": 35},  # #FF4D00
    "medium":   {"color": (1.0, 0.702, 0.0), "transparency": 30},  # #FFB300
    "low":      {"color": (0.0, 0.5, 1.0),   "transparency": 30},  # #0080FF
}
OVERLAY_PART_PREFIX = "DFM_OVERLAYS_FOR_"   # container that inherits transforms
ISSUE_PREFIX        = "DFM_Issue_"          # each issue is its own object
FACET_TEMP_SUFFIX   = "_FacetColor"

# Registries / globals
_DFM_BASES = set()
_DFM_OBSERVER = None
_DFM_TOOLTIP = None

# ---------- GEOM HELPERS ----------
def V(t): return FreeCAD.Vector(float(t[0]), float(t[1]), float(t[2]))

def get_mesh_from_object(obj, lin_def=0.1, ang_def=0.5):
    # Mesh::Feature → copy; Part::Feature (STEP) → tessellate
    if hasattr(obj, "Mesh"):
        return obj.Mesh.copy()
    if hasattr(obj, "Shape"):
        return MeshPart.meshFromShape(Shape=obj.Shape,
                                      LinearDeflection=float(lin_def),
                                      AngularDeflection=float(ang_def))
    raise ValueError(f"Object {obj.Name} is not meshable.")

def build_centers_and_tris(mesh):
    centers, tris = [], []
    for f in mesh.Facets:
        p1, p2, p3 = f.Points
        a, b, c = V(p1), V(p2), V(p3)
        centers.append(FreeCAD.Vector((a.x+b.x+c.x)/3.0, (a.y+b.y+c.y)/3.0, (a.z+b.z+c.z)/3.0))
        tris.append((a,b,c))
    return centers, tris

def nearest_face_index(p, centers):
    best_i, best_d2 = -1, inf
    for i, c in enumerate(centers):
        d2 = (c - p).Length ** 2
        if d2 < best_d2:
            best_i, best_d2 = i, d2
    return best_i

def project_point_to_triangle(p, a, b, c):
    ab, ac = b-a, c-a
    n = ab.cross(ac)
    nn = n.dot(n)
    if nn == 0:
        return min((a,b,c), key=lambda q: (q-p).Length)
    proj = p - n * ((p - a).dot(n) / nn)
    v0, v1, v2 = ab, ac, proj - a
    d00, d01, d11 = v0.dot(v0), v0.dot(v1), v1.dot(v1)
    d20, d21 = v2.dot(v0), v2.dot(v1)
    denom = d00*d11 - d01*d01
    if denom == 0:
        return min((a,b,c), key=lambda q: (q-p).Length)
    v = (d11*d20 - d01*d21) / denom
    w = (d00*d21 - d01*d20) / denom
    u = 1.0 - v - w
    u = max(0.0, min(1.0, u))
    v = max(0.0, min(1.0, v))
    if u + v > 1.0:
        s = u + v
        u, v = u/s, v/s
    w = 1.0 - u - v
    return a*u + b*v + c*w

def faces_within_radius(point, centers, r_mm):
    r2 = r_mm * r_mm
    return [i for i, c in enumerate(centers) if (c - point).Length**2 <= r2]

# ---------- CONTAINERS / TRANSFORMS ----------
def _overlay_part_name(base_name): return OVERLAY_PART_PREFIX + base_name

def _ensure_overlay_part(base_obj):
    doc = FreeCAD.ActiveDocument
    name = _overlay_part_name(base_obj.Name)
    part = doc.getObject(name)
    if not part:
        part = doc.addObject("App::Part", name)
    part.Placement = base_obj.Placement
    return part

def _clear_overlays_for(base_obj):
    doc = FreeCAD.ActiveDocument
    part = doc.getObject(_overlay_part_name(base_obj.Name))
    if part:
        for ch in list(part.Group):
            doc.removeObject(ch.Name)
        doc.removeObject(part.Name)
        doc.recompute()
    _DFM_BASES.discard(base_obj.Name)

def sync_overlay_part_to_base(base_obj_name):
    doc = FreeCAD.ActiveDocument
    base = doc.getObject(base_obj_name)
    if not base: return
    part = doc.getObject(_overlay_part_name(base_obj_name))
    if not part: return
    part.Placement = base.Placement

# ---------- PER-ISSUE OVERLAY BUILDER (Method 2) ----------
def _build_issue_overlay(mesh, face_indices, issue_idx, base_obj, severity, tooltip_text):
    if not face_indices:
        return None
    new_mesh = Mesh.Mesh()
    for idx in face_indices:
        facet = mesh.Facets[int(idx)]
        p1, p2, p3 = facet.Points
        new_mesh.addFacet(V(p1), V(p2), V(p3))

    doc = FreeCAD.ActiveDocument
    name = f"{ISSUE_PREFIX}{issue_idx:03d}"
    obj = doc.addObject("Mesh::Feature", name)
    obj.Mesh = new_mesh

    # Attach metadata for tooltip
    if not hasattr(obj, "addProperty"):
        return obj
    if "IssueTooltip" not in obj.PropertiesList:
        obj.addProperty("App::PropertyString", "IssueTooltip", "DFM", "Tooltip text for this DFM issue.")
    if "IssueSeverity" not in obj.PropertiesList:
        obj.addProperty("App::PropertyString", "IssueSeverity", "DFM", "Severity bucket.")
    obj.IssueTooltip = tooltip_text
    obj.IssueSeverity = severity

    # Style
    style = SEVERITY_STYLE.get(severity, SEVERITY_STYLE["medium"])
    vo = obj.ViewObject
    vo.ShapeColor = style["color"]
    vo.Transparency = int(style["transparency"])
    vo.DisplayMode = "Shaded"
    vo.Lighting = "One side"

    # Parent under overlay part so transforms follow the base
    part = _ensure_overlay_part(base_obj)
    part.addObject(obj)
    obj.Placement = FreeCAD.Placement()  # identity; inherit from part

    return obj

def dfm_visualize_per_issue(obj_name, issues, radius_mm=3.0, clear=True, lin_def=0.1, ang_def=0.5):
    """
    One overlay object per issue. Each gets IssueTooltip and IssueSeverity properties.
    """
    doc = FreeCAD.ActiveDocument
    base = doc.getObject(obj_name)
    if not base:
        raise ValueError(f"Base object '{obj_name}' not found.")

    if clear:
        _clear_overlays_for(base)

    mesh = get_mesh_from_object(base, lin_def, ang_def)
    centers, tris = build_centers_and_tris(mesh)

    created = []
    for k, it in enumerate(issues, start=1):
        pos = it.get("position")
        if not pos or len(pos) != 3:
            continue

        p = FreeCAD.Vector(float(pos[0]), float(pos[1]), float(pos[2]))
        fi = nearest_face_index(p, centers)
        if fi < 0: 
            continue
        a, b, c = tris[fi]
        p_proj = project_point_to_triangle(p, a, b, c)
        face_ids = faces_within_radius(p_proj, centers, radius_mm) or [fi]

        sev = (it.get("severity") or "medium").strip().lower()
        if sev not in SEVERITY_STYLE:
            sev = "medium"

        # Text for tooltip – choose the exact message you pass in
        tooltip_text = it.get("tooltip") or it.get("title") or "DFM Issue"
        if it.get("description"):
            tooltip_text = f"{tooltip_text}: {it['description']}"

        obj = _build_issue_overlay(mesh, face_ids, k, base, sev, tooltip_text)
        if obj:
            created.append(obj)

    sync_overlay_part_to_base(base.Name)
    _DFM_BASES.add(base.Name)
    FreeCAD.ActiveDocument.recompute()
    return created

# ---------- 3D-VIEW TOOLTIP CONTROLLER ----------
class _DfmTooltipController(QtWidgets.QLabel):
    """
    Shows a styled tooltip on top of the 3D view when hovering a DFM_Issue_* object.
    Click pins/unpins the tooltip.
    """
    def __init__(self, parent=None):
        super().__init__(parent)
        self.setWindowFlags(QtCore.Qt.ToolTip)
        self.setAttribute(QtCore.Qt.WA_TransparentForMouseEvents, False)
        self.setStyleSheet("""
            QLabel {
                background: rgba(30,30,30,220);
                color: #fff;
                border: 1px solid rgba(255,255,255,60);
                border-radius: 6px;
                padding: 6px 8px;
                font-size: 11pt;
            }
        """)
        self._pinned = False
        self.hide()

    def show_text(self, text, global_pos):
        self.setText(text)
        self.adjustSize()
        self.move(global_pos + QtCore.QPoint(12, 16))
        if not self._pinned:
            self.show()

    def pin_toggle(self):
        if self.isVisible():
            self._pinned = not self._pinned
            # Slight visual cue on pin
            if self._pinned:
                self.setStyleSheet(self.styleSheet() + "QLabel { border: 2px solid #4da3ff; }")
            else:
                self.setStyleSheet(self.styleSheet().replace("border: 2px solid #4da3ff;", "border: 1px solid rgba(255,255,255,60);"))

    def hide_if_unpinned(self):
        if not self._pinned:
            self.hide()

class _DfmDocObserver(object):
    """
    Auto-sync overlay part Placement with its base when base moves.
    Also wires up a hover/click handler that shows the tooltip.
    """
    def __init__(self):
        self._handler_installed = False
        self._view = FreeCADGui.ActiveDocument.ActiveView

        # Qt overlay tooltip widget
        global _DFM_TOOLTIP
        if _DFM_TOOLTIP is None:
            try:
                # Try to parent it to the 3D view widget so it stays on top
                parent_widget = self._view.getWidget()
                _DFM_TOOLTIP = _DfmTooltipController(parent=parent_widget)
            except Exception as e:
                FreeCAD.Console.PrintWarning(f"[DFM] Could not get 3D view widget: {e}, using no parent\n")
                # Fallback: create tooltip without parent
                _DFM_TOOLTIP = _DfmTooltipController(parent=None)

        # Install event callback once
        if not self._handler_installed:
            try:
                self._view.addEventCallback("SoEvent", self._on_event)
                self._handler_installed = True
            except Exception as e:
                FreeCAD.Console.PrintWarning(f"[DFM] Could not install event callback: {e}\n")

    def slotChangedObject(self, obj, prop):
        try:
            if prop == "Placement" and obj is not None and obj.Name in _DFM_BASES:
                part = FreeCAD.ActiveDocument.getObject(_overlay_part_name(obj.Name))
                if part:
                    part.Placement = obj.Placement
        except Exception as e:
            FreeCAD.Console.PrintError(f"[DFM] Observer error: {e}\n")

    def slotDeletedObject(self, obj):
        try:
            if obj is None: return
            name = getattr(obj, "Name", None)
            if not name: return
            if name in _DFM_BASES:
                part = FreeCAD.ActiveDocument.getObject(_overlay_part_name(name))
                if part:
                    for ch in list(part.Group):
                        FreeCAD.ActiveDocument.removeObject(ch.Name)
                    FreeCAD.ActiveDocument.removeObject(part.Name)
                _DFM_BASES.discard(name)
        except Exception as e:
            FreeCAD.Console.PrintError(f"[DFM] Observer delete error: {e}\n")

    def _on_event(self, info):
        """
        Hover: show IssueTooltip in 3D view when cursor is over a DFM_Issue_* object.
        Left click: pin/unpin tooltip.
        """
        try:
            etype = info.get("Type", "")
            pos = info.get("Position")  # Qt coords relative to view
            if pos is None:
                return

            # Click toggles pin when tooltip is visible/overlays
            if etype == "BUTTONDOWN" and info.get("Button") == "BUTTON1":
                if _DFM_TOOLTIP:
                    _DFM_TOOLTIP.pin_toggle()
                return

            # Mouse move → hit test
            if etype == "MOUSEMOVE":
                view = self._view
                hit = view.getObjectInfo(pos)
                # getObjectInfo returns dict with "Object", "Component", etc. when hitting a shape/mesh
                if hit and isinstance(hit, dict):
                    obj_name = hit.get("Object")
                    if obj_name and obj_name.startswith(ISSUE_PREFIX):
                        obj = FreeCAD.ActiveDocument.getObject(obj_name)
                        if obj and hasattr(obj, "IssueTooltip"):
                            # Translate view coords to global screen coords for widget placement
                            g = view.getWidget().mapToGlobal(QtCore.QPoint(pos[0], pos[1]))
                            _DFM_TOOLTIP.show_text(obj.IssueTooltip, g)
                            return
                # If not over an issue overlay, hide if not pinned
                if _DFM_TOOLTIP:
                    _DFM_TOOLTIP.hide_if_unpinned()
        except Exception as e:
            FreeCAD.Console.PrintError(f"[DFM] Hover handler error: {e}\n")

def enable_auto_sync_and_tooltips():
    global _DFM_OBSERVER
    if _DFM_OBSERVER is None:
        try:
            _DFM_OBSERVER = _DfmDocObserver()
            FreeCAD.addDocumentObserver(_DFM_OBSERVER)
            FreeCAD.Console.PrintMessage("[DFM] Auto-sync + 3D tooltips enabled.\n")
        except Exception as e:
            FreeCAD.Console.PrintWarning(f"[DFM] Could not enable full tooltip system: {e}\n")
            FreeCAD.Console.PrintMessage("[DFM] Using fallback selection-based tooltips.\n")

def disable_auto_sync_and_tooltips():
    global _DFM_OBSERVER
    try:
        if _DFM_OBSERVER is not None:
            view = FreeCADGui.ActiveDocument.ActiveView
            view.removeEventCallback("SoEvent", _DFM_OBSERVER._on_event)
            FreeCAD.removeDocumentObserver(_DFM_OBSERVER)
    except Exception:
        pass
    _DFM_OBSERVER = None
    FreeCAD.Console.PrintMessage("[DFM] Auto-sync + 3D tooltips disabled.\n")

# ---------- PUBLIC API ----------
def dfm_draw_per_issue_overlays(obj_name, issues, radius_mm=3.0, clear=True,
                                lin_def=0.1, ang_def=0.5):
    """
    Main entry: builds ONE overlay per issue (surface-aligned triangles),
    assigns per-issue tooltip text, and enables hover tooltips.
    """
    out = dfm_visualize_per_issue(obj_name, issues, radius_mm, clear, lin_def, ang_def)
    enable_auto_sync_and_tooltips()
    return out

def dfm_toggle_overlays(obj_name, visible=True):
    part = FreeCAD.ActiveDocument.getObject(OVERLAY_PART_PREFIX + obj_name)
    if not part:
        FreeCAD.Console.PrintMessage("[DFM] No overlays to toggle.\n")
        return
    part.ViewObject.Visibility = bool(visible)
    for ch in part.Group:
        ch.ViewObject.Visibility = bool(visible)

# ========== END PROFESSIONAL DFM OVERLAY/TOOLTIP SYSTEM ==========

# Try to import Claude AI (Anthropic) for conversational CAD generation
try:
    import anthropic
    ANTHROPIC_AVAILABLE = True
    print("[OK] Claude AI (Anthropic) integration available")
except ImportError:
    ANTHROPIC_AVAILABLE = False
    print("⚠️ Claude AI integration not available - install anthropic package")

# Robust environment variable loading for FreeCAD's Python environment
ANTHROPIC_API_KEY = None
try:
    import os
    
    # Method 1: Try environment variables first
    ANTHROPIC_API_KEY = os.getenv('ANTHROPIC_API_KEY') or os.environ.get('ANTHROPIC_API_KEY')
    
    # Method 2: If not found, try to load directly from .env file (FreeCAD-compatible)
    if not ANTHROPIC_API_KEY:
        project_dir = os.path.dirname(os.path.abspath(__file__))
        env_file = os.path.join(project_dir, '.env')
        
        if os.path.exists(env_file):
            print(f"Loading environment variables directly from {env_file}")
            with open(env_file, 'r') as f:
                for line in f:
                    line = line.strip()
                    if line and not line.startswith('#') and '=' in line:
                        key, value = line.split('=', 1)
                        key = key.strip()
                        value = value.strip().strip('"').strip("'")
                        if key == 'ANTHROPIC_API_KEY':
                            ANTHROPIC_API_KEY = value
                            os.environ[key] = value  # Set in environment for other components
                            break
    
    # Method 3: Try python-dotenv if available (fallback)
    if not ANTHROPIC_API_KEY:
        try:
            from dotenv import load_dotenv
            project_dir = os.path.dirname(os.path.abspath(__file__))
            env_file = os.path.join(project_dir, '.env')
            if os.path.exists(env_file):
                load_dotenv(env_file)
                ANTHROPIC_API_KEY = os.getenv('ANTHROPIC_API_KEY')
                print(f"[OK] Environment variables loaded via python-dotenv from {env_file}")
            else:
                load_dotenv()
                ANTHROPIC_API_KEY = os.getenv('ANTHROPIC_API_KEY')
                print("[OK] Environment variables loaded via python-dotenv")
        except ImportError:
            print("⚠️ python-dotenv not available - using direct file reading")
    
    if ANTHROPIC_API_KEY:
        print("[OK] ANTHROPIC_API_KEY found - Claude integration enabled")
        print(f"   API key starts with: {ANTHROPIC_API_KEY[:10]}...")
    else:
        print("⚠️ ANTHROPIC_API_KEY not found - Claude integration disabled")
        
except Exception as e:
    print(f"⚠️ Error loading ANTHROPIC_API_KEY: {e}")
    ANTHROPIC_API_KEY = None

# Try to import cloud services
try:
    from cloud_services.cloud_integration import CloudIntegration
    from utils.cad_extractor import extract_cad_data_for_features
    from text_to_cad_integration import TextToCADIntegration
    _CLOUD_SERVICES_AVAILABLE = True
except ImportError:
    print("Warning: Cloud services not available. Some features will be disabled.")
    _CLOUD_SERVICES_AVAILABLE = False

# Try to import cloud integration functions
try:
    from cloud_integration_functions import (
        analyze_dfm, estimate_cost, recommend_tools, 
        compare_manufacturing_methods, call_feature
    )
    _CLOUD_FUNCTIONS_AVAILABLE = True
except ImportError:
    print("Warning: Cloud integration functions not available. Using built-in call_feature.")
    _CLOUD_FUNCTIONS_AVAILABLE = False

# ===============================
# DFM Selection Observer for Tooltips
# ===============================
class DFMSelectionObserver:
    """Observer to handle selection of DFM highlighted objects and show tooltips"""
    
    def __init__(self, task_panel=None):
        self.task_panel = task_panel
        self.dfm_highlights = {}  # Store highlight info: {object_name: issue_description}
        print(f"DEBUG: DFMSelectionObserver initialized with task_panel: {task_panel is not None}")
    
    def addSelection(self, doc, obj, sub, pnt):
        """Called when an object is selected"""
        try:
            obj_name = obj
            print(f"DEBUG: DFM Selection - Object: {obj_name}, Sub: {sub}, Point: {pnt}")
            print(f"DEBUG: Available DFM highlights: {list(self.dfm_highlights.keys())}")
            
            # Get the actual FreeCAD object to check its properties
            try:
                import FreeCAD
                if hasattr(FreeCAD, 'ActiveDocument') and FreeCAD.ActiveDocument:
                    fc_obj = FreeCAD.ActiveDocument.getObject(obj_name)
                    if fc_obj:
                        print(f"DEBUG: Object type: {fc_obj.TypeId}, Label: {fc_obj.Label}")
                        if hasattr(fc_obj, 'Name'):
                            print(f"DEBUG: Object Name: {fc_obj.Name}")
            except Exception as e:
                print(f"DEBUG: Could not get FreeCAD object details: {e}")
            
            # Check if this is a DFM highlighted object (direct match)
            if obj_name in self.dfm_highlights:
                print(f"DEBUG: [OK] Direct match found for DFM highlight: {obj_name}")
            # Also check if the object name starts with DFM_Issue_ (in case of naming variations)
            elif obj_name.startswith('DFM_Issue_'):
                print(f"DEBUG: [OK] DFM_Issue pattern match found: {obj_name}")
                # Try to find the closest match in our highlights
                for highlight_key in self.dfm_highlights.keys():
                    if highlight_key == obj_name or obj_name in highlight_key:
                        obj_name = highlight_key
                        print(f"DEBUG: Using highlight key: {highlight_key}")
                        break
            else:
                print(f"DEBUG: ❌ No DFM highlight match found for: {obj_name}")
                # Check if any DFM highlights exist in the document
                try:
                    import FreeCAD
                    if hasattr(FreeCAD, 'ActiveDocument') and FreeCAD.ActiveDocument:
                        doc_obj_names = [obj.Name for obj in FreeCAD.ActiveDocument.Objects]
                        dfm_objects = [name for name in doc_obj_names if name.startswith('DFM_Issue_')]
                        print(f"DEBUG: DFM objects in document: {dfm_objects}")
                except:
                    pass
            
            # Process the DFM highlight if found
            if obj_name in self.dfm_highlights:
                issue_description = self.dfm_highlights[obj_name]
                print(f"DEBUG: DFM Tooltip - {issue_description}")
                
                # Show tooltip in FreeCAD status bar
                try:
                    import FreeCADGui
                    if hasattr(FreeCADGui, 'getMainWindow'):
                        main_window = FreeCADGui.getMainWindow()
                        if hasattr(main_window, 'statusBar'):
                            status_bar = main_window.statusBar()
                            status_bar.showMessage(f"DFM Issue: {issue_description}", 5000)  # Show for 5 seconds
                            print("DEBUG: DFM tooltip shown in status bar")
                except Exception as e:
                    print(f"DEBUG: Failed to show status bar message: {e}")
                
                # Show as popup tooltip in 3D view with enhanced visibility
                try:
                    import FreeCADGui
                    from PySide2 import QtWidgets, QtCore, QtGui
                    
                    # Get the 3D view widget
                    mdi = FreeCADGui.getMainWindow().findChild(QtWidgets.QMdiArea)
                    if mdi and mdi.activeSubWindow():
                        view_widget = mdi.activeSubWindow().widget()
                        if view_widget:
                            # Create a more visible tooltip with rich formatting
                            cursor_pos = QtGui.QCursor.pos()
                            
                            # Enhanced tooltip with better formatting
                            tooltip_text = f"""<div style='background-color: #ffffcc; padding: 8px; border: 2px solid #ff6600; border-radius: 4px;'>
<b style='color: #cc0000;'>🔍 DFM Manufacturing Issue</b><br/>
<span style='color: #000000;'>{issue_description}</span><br/>
<i style='color: #666666; font-size: 10px;'>Click for details in Manufacturing Issues section</i>
</div>"""
                            
                            # Show enhanced tooltip at cursor position
                            QtWidgets.QToolTip.showText(cursor_pos, tooltip_text, view_widget, QtCore.QRect(), 8000)  # Show for 8 seconds
                            print("DEBUG: Enhanced DFM tooltip shown as 3D view popup")
                            
                            # Also create a temporary message box for critical issues
                            if 'critical' in issue_description.lower() or 'thin wall' in issue_description.lower():
                                try:
                                    # Create a non-blocking message for critical issues
                                    msg = QtWidgets.QMessageBox()
                                    msg.setIcon(QtWidgets.QMessageBox.Warning)
                                    msg.setWindowTitle("Critical DFM Issue Detected")
                                    msg.setText(f"⚠️ {issue_description}")
                                    msg.setInformativeText("This issue requires immediate attention for successful manufacturing.")
                                    msg.setStandardButtons(QtWidgets.QMessageBox.Ok)
                                    msg.setDefaultButton(QtWidgets.QMessageBox.Ok)
                                    
                                    # Show non-blocking
                                    msg.show()
                                    print("DEBUG: Critical issue popup shown")
                                except Exception as popup_e:
                                    print(f"DEBUG: Failed to show critical issue popup: {popup_e}")
                                    
                except Exception as e:
                    print(f"DEBUG: Failed to show 3D view tooltip: {e}")
                    # Fallback to simple tooltip
                    try:
                        from PySide2 import QtWidgets
                        QtWidgets.QToolTip.showText(QtGui.QCursor.pos(), f"DFM Issue: {issue_description}")
                        print("DEBUG: Fallback tooltip shown")
                    except:
                        pass
                
                # Show detailed information in chat interface if available
                try:
                    if self.task_panel and hasattr(self.task_panel, 'add_system_message'):
                        # Find the full issue details from the stored highlights
                        full_issue_info = None
                        for highlight_key, highlight_data in self.dfm_highlights.items():
                            if highlight_key == obj_name and isinstance(highlight_data, dict):
                                full_issue_info = highlight_data
                                break
                        
                        if full_issue_info:
                            severity = full_issue_info.get('severity', 'unknown')
                            issue_type = full_issue_info.get('type', 'unknown')
                            recommendations = full_issue_info.get('recommendations', [])
                            
                            # Create detailed message for chat interface
                            severity_emoji = {
                                'critical': '🔴',
                                'high': '🟠', 
                                'medium': '🟡',
                                'low': '🔵'
                            }.get(severity, '⚪')
                            
                            detailed_msg = f"""
{severity_emoji} **Selected DFM Issue Details:**
**Type:** {issue_type.replace('_', ' ').title()}
**Severity:** {severity.title()}
**Description:** {issue_description}

**Recommendations:**"""
                            
                            if recommendations:
                                for i, rec in enumerate(recommendations[:3], 1):  # Show first 3 recommendations
                                    detailed_msg += f"\n{i}. {rec}"
                            else:
                                detailed_msg += "\n• Review geometry for manufacturability"
                            
                            self.task_panel.add_system_message(detailed_msg)
                            print("DEBUG: Detailed DFM issue info added to chat interface")
                        else:
                            # Fallback message
                            self.task_panel.add_system_message(f"🔍 **Selected DFM Issue:** {issue_description}")
                            print("DEBUG: Basic DFM issue info added to chat interface")
                except Exception as chat_e:
                    print(f"DEBUG: Failed to show issue in chat interface: {chat_e}")
                
                # Also show in console for debugging
                try:
                    import FreeCAD
                    FreeCAD.Console.PrintMessage(f"DFM Issue Selected: {issue_description}\n")
                except:
                    pass
                    
        except Exception as e:
            print(f"DEBUG: DFM Selection error: {e}")
    
    def update_highlights(self, highlights_dict):
        """Update the stored highlight information"""
        self.dfm_highlights = highlights_dict
        print(f"DEBUG: Updated DFM highlights: {list(highlights_dict.keys())}")
        
    def set_task_panel(self, task_panel):
        """Update the task panel reference for tooltip display"""
        self.task_panel = task_panel
        print(f"DEBUG: DFM observer task panel updated: {task_panel is not None}")
    
    def setSelection(self, doc):
        """Called when selection is set"""
        pass
    
    def clearSelection(self, doc):
        """Called when selection is cleared"""
        pass

# ===============================
# Manufacturing Feature Manager
# ===============================
class ManufacturingFeatureManager:
    """Manages manufacturing features like DFM, cost estimation, and tool recommendations"""
    
    def __init__(self):
        """Initialize the manufacturing feature manager"""
        self.last_dfm_result = None
        self.last_cost_result = None
        self.last_tool_result = None
        self.cloud_integration = None
        
        # Try to initialize cloud integration
        if _CLOUD_SERVICES_AVAILABLE:
            try:
                from cloud_services.cloud_integration import CloudIntegration
                this_dir = os.path.dirname(os.path.abspath(__file__))
                config_path = os.path.join(this_dir, "cloud_config.json")
                self.cloud_integration = CloudIntegration(config_path)
                print("Cloud integration initialized for manufacturing features")
            except Exception as e:
                print(f"Error initializing cloud integration: {str(e)}")
                traceback.print_exc()
    
    def analyze_dfm(self, manufacturing_process="3d_printing", material="pla", production_volume=1, advanced_analysis=True):
        """Analyze design for manufacturability using industry-grade DFM engine"""
        try:
            # Use cloud integration if available
            if self.cloud_integration:
                result = self.cloud_integration.analyze_dfm(
                    manufacturing_process=manufacturing_process,
                    material=material,
                    production_volume=production_volume,
                    advanced_analysis=advanced_analysis
                )
                
                # Check if cloud service failed to provide detailed analysis
                if result and result.get('success'):
                    data = result.get('data', {})
                    design_issues = data.get('design_issues', [])
                    
                    # Check if cloud returned "Unable to perform detailed analysis"
                    has_insufficient_analysis = any(
                        isinstance(issue, str) and 'Unable to perform detailed analysis' in issue
                        for issue in design_issues
                    )
                    
                    if has_insufficient_analysis:
                        print("🔄 Cloud DFM returned insufficient analysis, using comprehensive geometric analysis...")
                        
                        try:
                            # DIRECT COMPREHENSIVE GEOMETRIC ANALYSIS
                            print("🔍 Performing comprehensive geometric analysis...")
                            
                            # Extract CAD data for analysis
                            cad_data = extract_cad_data_for_features()
                            
                            # Perform comprehensive geometric analysis using our implemented logic
                            geometric_issues = self._perform_comprehensive_geometric_analysis()
                            
                            if geometric_issues and len(geometric_issues) > 0:
                                print(f"🎯 Comprehensive analysis found {len(geometric_issues)} specific geometric issues")
                                
                                # Create enhanced result with geometric findings
                                enhanced_result = self._create_geometric_dfm_result(
                                    cloud_result=result,
                                    geometric_issues=geometric_issues,
                                    manufacturing_process=manufacturing_process,
                                    material=material,
                                    production_volume=production_volume
                                )
                                
                                print("🎆 Comprehensive geometric analysis complete - real manufacturing issues identified!")
                                self.last_dfm_result = enhanced_result
                                return enhanced_result
                            else:
                                print("⚠️ No specific geometric issues found, using cloud result")
                            
                            # FALLBACK TO BASIC ANALYSIS IF NO GEOMETRIC ISSUES FOUND
                            print("🔄 Using basic manufacturability analysis...")
                            
                            # Initialize enhanced local analyzer
                            local_analyzer = EnhancedLocalDFMAnalyzer()
                            
                            # Perform enhanced local analysis
                            local_result = local_analyzer.analyze_dfm(
                                cad_data=cad_data,
                                manufacturing_process=manufacturing_process,
                                material=material,
                                production_volume=production_volume
                            )
                            
                            if local_result.get('success'):
                                print("[OK] Enhanced local DFM analysis successful!")
                                
                                # Create hybrid result combining cloud + local insights
                                hybrid_result = self._create_hybrid_dfm_result(
                                    cloud_result=result,
                                    local_result=local_result,
                                    manufacturing_process=manufacturing_process,
                                    material=material,
                                    production_volume=production_volume
                                )
                                
                                print("🎆 Hybrid DFM analysis complete - combining cloud AI + local expertise!")
                                self.last_dfm_result = hybrid_result
                                return hybrid_result
                            else:
                                print("❌ Enhanced local DFM analysis failed, using cloud result")
                                
                        except Exception as local_e:
                            print(f"Enhanced local DFM analysis error: {str(local_e)}")
                
                self.last_dfm_result = result
                return result
            # Otherwise use cloud functions if available
            elif _CLOUD_FUNCTIONS_AVAILABLE:
                result = analyze_dfm(manufacturing_process, material, production_volume)
                self.last_dfm_result = result
                return result
            # Fall back to direct API call
            else:
                payload = {
                    "manufacturing_process": manufacturing_process,
                    "material": material,
                    "production_volume": production_volume,
                    "advanced_analysis": advanced_analysis,
                    "cad_data": extract_cad_data_for_features()
                }
                result = call_feature("dfm_analysis", payload)
                self.last_dfm_result = result
                return result
                
        except Exception as e:
            print(f"Error in DFM analysis: {str(e)}")
            traceback.print_exc()
            
            # Try enhanced local DFM analysis as fallback
            try:
                print("🔄 Attempting enhanced local DFM analysis...")
                from utils.enhanced_local_dfm import EnhancedLocalDFMAnalyzer
                
                # Extract CAD data for local analysis
                cad_data = extract_cad_data_for_features()
                
                # Initialize enhanced local analyzer
                local_analyzer = EnhancedLocalDFMAnalyzer()
                
                # Perform enhanced local analysis
                result = local_analyzer.analyze_dfm(
                    cad_data=cad_data,
                    manufacturing_process=manufacturing_process,
                    material=material,
                    production_volume=production_volume
                )
                
                if result.get('success'):
                    print("[OK] Enhanced local DFM analysis successful!")
                    self.last_dfm_result = result
                    return result
                else:
                    print("❌ Enhanced local DFM analysis failed")
                    
            except Exception as local_e:
                print(f"Enhanced local DFM analysis error: {str(local_e)}")
            
            return {
                "success": False,
                "error": str(e),
                "service": "dfm",
                "timestamp": time.strftime("%Y-%m-%dT%H:%M:%S")
            }
    
    def _create_hybrid_dfm_result(self, cloud_result, local_result, manufacturing_process, material, production_volume):
        """Create a hybrid DFM result combining cloud AI insights with enhanced local analysis"""
        try:
            # Get data from both sources
            cloud_data = cloud_result.get('data', {})
            local_data = local_result.get('data', {})
            
            # Start with the enhanced local analysis as the base (more accurate for Indian market)
            hybrid_data = local_data.copy()
            
            # Enhance with cloud AI insights where available
            # 1. Use cloud's material suggestions if they exist and are meaningful
            cloud_materials = cloud_data.get('material_suggestions', [])
            if cloud_materials and cloud_materials != ['ABS', 'PLA', 'Aluminum']:  # Not generic
                hybrid_data['alternative_materials'] = cloud_materials
            
            # 2. Use cloud's process recommendations if they exist and are meaningful
            cloud_processes = cloud_data.get('process_recommendations', [])
            if cloud_processes and cloud_processes != ['3D Printing', 'CNC Machining']:  # Not generic
                hybrid_data['alternative_processes_ai'] = cloud_processes
            
            # 3. Combine manufacturing features analysis
            cloud_features = cloud_data.get('manufacturing_features', {})
            if cloud_features:
                hybrid_data['ai_insights'] = {
                    'complexity_rating': cloud_features.get('complexity_rating', 'Unknown'),
                    'moldability_score': cloud_features.get('moldability_score', 0),
                    'ai_analysis_available': True
                }
            else:
                hybrid_data['ai_insights'] = {
                    'ai_analysis_available': False,
                    'note': 'Cloud AI analysis not available for this geometry'
                }
            
            # 4. PRESERVE DESIGN_ISSUES FROM CLOUD DATA (PROBLEM AREAS BUTTON FIX)
            cloud_design_issues = cloud_data.get('design_issues', [])
            if cloud_design_issues:
                hybrid_data['design_issues'] = cloud_design_issues
                print(f"DEBUG: Preserved {len(cloud_design_issues)} design_issues in hybrid result")
            
            # 5. Enhanced analysis summary
            hybrid_data['analysis_summary'] = {
                'primary_analysis': 'Enhanced Local DFM (Indian Market Focus)',
                'ai_enhancement': 'Cloud AI Insights' if cloud_features else 'Not Available',
                'cost_analysis': 'Verified Indian Market Rates',
                'supplier_context': 'Indian Manufacturing Ecosystem',
                'confidence_level': 'High' if cloud_features else 'Medium'
            }
            
            # 5. Add hybrid service identifier
            hybrid_result = {
                'success': True,
                'data': hybrid_data,
                'service': 'hybrid_dfm_cloud_local',
                'timestamp': local_result.get('timestamp', ''),
                'analysis_components': {
                    'enhanced_local_dfm': True,
                    'cloud_ai_insights': bool(cloud_features),
                    'indian_market_context': True,
                    'verified_rates': True
                }
            }
            
            return hybrid_result
            
        except Exception as e:
            print(f"Error creating hybrid DFM result: {str(e)}")
            # Fallback to local result if hybrid creation fails
            return local_result
    
    def _create_claude_dfm_result(self, cloud_result, claude_result, manufacturing_process, material, production_volume):
        """Create a DFM result combining cloud data with Claude's advanced issue detection"""
        try:
            # Get data from both sources
            cloud_data = cloud_result.get('data', {})
            claude_issues = claude_result.get('issues', [])
            claude_recommendations = claude_result.get('recommendations', [])
            severity_summary = claude_result.get('severity_summary', {})
            
            # Create enhanced data structure with Claude's findings
            enhanced_data = {
                # Preserve cloud geometry analysis
                'geometry_summary': cloud_data.get('geometry_summary', {}),
                'cost_analysis': cloud_data.get('cost_analysis', {}),
                'process_recommendations': cloud_data.get('process_recommendations', []),
                'material_suggestions': cloud_data.get('material_suggestions', []),
                
                # Add Claude's advanced issue detection
                'manufacturing_issues': [],
                'design_issues': [],  # For UI compatibility
                'manufacturability_score': self._calculate_score_from_issues(claude_issues),
                'overall_rating': self._get_rating_from_score(self._calculate_score_from_issues(claude_issues)),
                
                # Enhanced recommendations combining both sources
                'recommendations': claude_recommendations,
                
                # Claude-specific insights
                'claude_analysis': {
                    'issues_detected': len(claude_issues),
                    'severity_breakdown': severity_summary,
                    'analysis_type': 'advanced_ai_detection',
                    'manufacturing_focus': manufacturing_process
                },
                
                # Analysis metadata
                'analysis_summary': {
                    'primary_analysis': 'Claude AI Advanced DFM Detection',
                    'ai_enhancement': 'Anthropic Claude API',
                    'issue_detection': 'Real Manufacturing Problems Identified',
                    'confidence_level': 'Very High'
                }
            }
            
            # Convert Claude issues to both formats for compatibility
            for issue in claude_issues:
                # Format for manufacturing_issues (detailed)
                manufacturing_issue = {
                    'title': issue.get('title', 'Manufacturing Issue'),
                    'severity': issue.get('severity', 'medium'),
                    'description': issue.get('description', ''),
                    'recommendation': issue.get('recommendation', ''),
                    'type': issue.get('type', 'manufacturing_issue'),
                    'location': issue.get('location', 'geometry'),
                    'impact': issue.get('impact', 'Affects manufacturing quality'),
                    'position': issue.get('position', {'x': 0, 'y': 0, 'z': 0})
                }
                enhanced_data['manufacturing_issues'].append(manufacturing_issue)
                
                # Format for design_issues (UI compatibility)
                design_issue = {
                    'severity': issue.get('severity', 'medium'),
                    'description': f"{issue.get('title', 'Issue')}: {issue.get('description', '')}",
                    'recommendation': issue.get('recommendation', ''),
                    'type': issue.get('type', 'manufacturing_issue'),
                    'position': issue.get('position', {'x': 0, 'y': 0, 'z': 0})
                }
                enhanced_data['design_issues'].append(design_issue)
            
            print(f"DEBUG: Claude result created with {len(enhanced_data['manufacturing_issues'])} issues")
            print(f"DEBUG: Claude result created with {len(enhanced_data['design_issues'])} design_issues")
            
            # Create final result structure
            claude_dfm_result = {
                'success': True,
                'data': enhanced_data,
                'service': 'claude_dfm_advanced',
                'timestamp': claude_result.get('timestamp', ''),
                'analysis_components': {
                    'claude_ai_detection': True,
                    'cloud_geometry_analysis': True,
                    'real_issue_identification': True,
                    'manufacturing_focused': True
                }
            }
            
            return claude_dfm_result
            
        except Exception as e:
            print(f"Error creating Claude DFM result: {str(e)}")
            # Fallback to cloud result if Claude integration fails
            return cloud_result
    
    def _calculate_score_from_issues(self, issues):
        """Calculate manufacturability score based on Claude's issue detection"""
        if not issues:
            return 95  # High score if no issues found
        
        # Start with perfect score and deduct based on severity
        score = 100
        for issue in issues:
            severity = issue.get('severity', 'medium')
            if severity == 'critical':
                score -= 25
            elif severity == 'high':
                score -= 15
            elif severity == 'medium':
                score -= 8
            elif severity == 'low':
                score -= 3
        
        return max(score, 10)  # Minimum score of 10
    
    def _get_rating_from_score(self, score):
        """Convert numeric score to rating"""
        if score >= 90:
            return 'excellent'
        elif score >= 75:
            return 'good'
        elif score >= 60:
            return 'fair'
        else:
            return 'poor'
    
    def estimate_cost(self, manufacturing_process="3d_printing", material="pla", quantity=1, region="global"):
        """Estimate manufacturing cost"""
        try:
            # Use cloud integration if available
            if self.cloud_integration:
                result = self.cloud_integration.estimate_cost(
                    manufacturing_process=manufacturing_process,
                    material=material,
                    quantity=quantity,
                    region=region
                )
                self.last_cost_result = result
                return result
            # Otherwise use cloud functions if available
            elif _CLOUD_FUNCTIONS_AVAILABLE:
                result = estimate_cost(
                    manufacturing_process=manufacturing_process,
                    material=material,
                    quantity=quantity,
                    region=region
                )
                self.last_cost_result = result
                return result
            # Fall back to direct API call
            else:
                payload = {
                    "manufacturing_process": manufacturing_process,
                    "material": material,
                    "quantity": quantity,
                    "region": region,
                    "cad_data": extract_cad_data_for_features()
                }
                result = call_feature("cost_estimate", payload)
                self.last_cost_result = result
                return result
        except Exception as e:
            print(f"Error in cost estimation: {str(e)}")
            traceback.print_exc()
            return {
                "success": False,
                "error": str(e),
                "service": "cost",
                "timestamp": time.strftime("%Y-%m-%dT%H:%M:%S")
            }
    
    def recommend_tools(self, manufacturing_process="cnc_machining", material="aluminum", machine_type=None):
        """Get tool recommendations"""
        try:
            # Use cloud integration if available
            if self.cloud_integration:
                result = self.cloud_integration.recommend_tools(
                    manufacturing_process=manufacturing_process,
                    material=material,
                    machine_type=machine_type
                )
                self.last_tool_result = result
                return result
            # Otherwise use cloud functions if available
            elif _CLOUD_FUNCTIONS_AVAILABLE:
                result = recommend_tools(
                    manufacturing_process=manufacturing_process,
                    material=material,
                    machine_type=machine_type
                )
                self.last_tool_result = result
                return result
            # Fall back to direct API call
            else:
                payload = {
                    "manufacturing_process": manufacturing_process,
                    "material": material,
                    "machine_type": machine_type,
                    "cad_data": extract_cad_data_for_features()
                }
                result = call_feature("tool_recommendation", payload)
                self.last_tool_result = result
                return result
        except Exception as e:
            print(f"Error in tool recommendation: {str(e)}")
            traceback.print_exc()
            return {
                "success": False,
                "error": str(e),
                "service": "tool_recommendation",
                "timestamp": time.strftime("%Y-%m-%dT%H:%M:%S")
            }
    
    def compare_manufacturing_methods(self, materials=None, processes=None, quantities=None):
        """Compare costs across different manufacturing methods"""
        try:
            if materials is None:
                materials = ["pla", "abs", "nylon"]
            if processes is None:
                processes = ["3d_printing", "cnc_machining", "injection_molding"]
            if quantities is None:
                quantities = [1, 10, 100, 1000]
                
            # Use cloud integration if available
            if self.cloud_integration:
                return self.cloud_integration.compare_manufacturing_methods(
                    materials=materials,
                    processes=processes,
                    quantities=quantities
                )
            # Otherwise use cloud functions if available
            elif _CLOUD_FUNCTIONS_AVAILABLE:
                return compare_manufacturing_methods(
                    materials=materials,
                    processes=processes,
                    quantities=quantities
                )
            # Fall back to direct API call
            else:
                payload = {
                    "materials": materials,
                    "processes": processes,
                    "quantities": quantities,
                    "cad_data": extract_cad_data_for_features()
                }
                return call_feature("manufacturing_comparison", payload)
        except Exception as e:
            print(f"Error in manufacturing comparison: {str(e)}")
            traceback.print_exc()
            return {
                "success": False,
                "error": str(e),
                "service": "manufacturing_comparison",
                "timestamp": time.strftime("%Y-%m-%dT%H:%M:%S")
            }
    
    def visualize_dfm_issues(self):
        """Visualize DFM issues in the FreeCAD view using enhanced visualization"""
        try:
            # BYPASS the problematic cloud_integration method and use direct visualization
            # The cloud_integration.visualize_dfm_issues() has a get_dfm_issues() call that returns wrong cached data
            print("DEBUG: Using direct visualization to bypass cloud_integration issues")
            
            if self.last_dfm_result and self.last_dfm_result.get("success", False):
                # Basic visualization if cloud integration not available
                data = self.last_dfm_result.get("data", {})
                
                # Try to get issues from multiple sources (Claude-detected manufacturing_issues first)
                issues = data.get("manufacturing_issues", [])
                if not issues:
                    # Fallback to design_issues if manufacturing_issues not available
                    issues = data.get("design_issues", [])
                if not issues:
                    # Final fallback to legacy issues format
                    issues = data.get("issues", [])
                
                print(f"DEBUG: Found {len(issues)} issues to visualize")
                if issues:
                    print(f"DEBUG: First issue: {issues[0]}")
                
                if not issues:
                    print("No DFM issues to visualize")
                    return False
                
                # Get active document and preserve it
                doc = FreeCAD.ActiveDocument
                if not doc:
                    print("No active document")
                    return
                
                # Store the current document name to prevent switching
                current_doc_name = doc.Name
                print(f"DEBUG: Visualizing on document: {current_doc_name}")
                
                # Remove any existing DFM visualization
                self._remove_existing_dfm_visualization(doc)
                    
                # Create a group for DFM issues
                dfm_group = doc.addObject("App::DocumentObjectGroup", "DFM_Issues")
                
                # ROBUST DFM OVERLAY SYSTEM: Professional surface-aligned highlighting
                print(f"DEBUG: Creating robust DFM overlays for {len(issues)} issues...")
                
                # Use the professional DFM visualization system
                try:
                    # Find the mesh/CAD object to highlight
                    target_obj = None
                    for obj in doc.Objects:
                        if hasattr(obj, 'Mesh') or hasattr(obj, 'Shape'):
                            target_obj = obj
                            break
                    
                    if target_obj:
                        print(f"DEBUG: Found target object: {target_obj.Name}")
                        # Use the robust DFM visualization system
                        created_overlays = self._dfm_visualize(target_obj.Name, issues, method="overlay", radius_mm=3.0)
                        print(f"DEBUG: Created {len(created_overlays) if created_overlays else 0} professional DFM overlays")
                    else:
                        print("DEBUG: No suitable mesh or CAD object found for overlay visualization")
                        
                except Exception as overlay_error:
                    print(f"DEBUG: Professional overlay system failed: {overlay_error}")
                    print("DEBUG: Falling back to chat-only DFM analysis")
                
                # NOTE: Arrow visualization logic preserved for future use if needed
                # Can be re-enabled by calling self._create_arrow_visualization_BACKUP()
                
                # Recompute document and refresh view to ensure visibility
                doc.recompute()
                
                # Force view refresh to make rectangles visible
                try:
                    import FreeCADGui
                    if hasattr(FreeCADGui, 'ActiveDocument') and FreeCADGui.ActiveDocument:
                        FreeCADGui.ActiveDocument.ActiveView.fitAll()
                        FreeCADGui.updateGui()
                    print(f"DEBUG: Document recomputed and view refreshed - {len(issues)} DFM rectangles should now be visible")
                except Exception as e:
                    print(f"DEBUG: View refresh failed: {e}")
                
                # Activate DFM selection observer for tooltip functionality
                try:
                    import FreeCADGui
                    if hasattr(FreeCADGui, 'Selection'):
                        # Remove any existing DFM observer
                        try:
                            if hasattr(self, 'dfm_observer'):
                                FreeCADGui.Selection.removeObserver(self.dfm_observer)
                        except:
                            pass
                        
                        # Create and add new DFM observer with task panel access
                        # Find the task panel instance for tooltip display
                        task_panel = None
                        try:
                            # Look for the active StandaloneCoPilotTaskPanel instance
                            import FreeCADGui
                            if hasattr(FreeCADGui, 'Control') and hasattr(FreeCADGui.Control, 'activeDialog'):
                                active_dialog = FreeCADGui.Control.activeDialog()
                                if hasattr(active_dialog, 'add_system_message'):
                                    task_panel = active_dialog
                        except:
                            pass
                        
                        self.dfm_observer = DFMSelectionObserver(task_panel=task_panel)
                        FreeCADGui.Selection.addObserver(self.dfm_observer)
                        print("DEBUG: DFM selection observer activated for tooltip functionality with chat interface")
                        
                        # Populate tooltip information for the rectangles
                        # Use same naming format as professional overlay system (3-digit format)
                        tooltip_info = {}
                        for i, issue in enumerate(issues):
                            rect_name = f"DFM_Issue_{i+1:03d}"  # Match professional overlay naming: DFM_Issue_001, etc.
                            tooltip_text = issue.get('title', 'Manufacturing Issue')
                            description = issue.get('description', 'Manufacturing issue detected')
                            tooltip_info[rect_name] = f"{tooltip_text}: {description}"
                        
                        # Update the observer with tooltip information
                        self.dfm_observer.update_highlights(tooltip_info)
                        print(f"DEBUG: Updated DFM observer with {len(tooltip_info)} tooltip entries")
                except Exception as e:
                    print(f"DEBUG: Failed to activate DFM selection observer: {e}")
                
                # CRITICAL: Ensure we stay on the original document
                try:
                    target_doc = FreeCAD.getDocument(current_doc_name)
                    if target_doc and FreeCAD.ActiveDocument != target_doc:
                        print(f"DEBUG: Switching back to original document: {current_doc_name}")
                        FreeCAD.setActiveDocument(current_doc_name)
                        import FreeCADGui
                        if hasattr(FreeCADGui, 'ActiveDocument'):
                            FreeCADGui.ActiveDocument = FreeCADGui.getDocument(current_doc_name)
                    else:
                        print(f"DEBUG: Already on correct document: {current_doc_name}")
                except Exception as e:
                    print(f"DEBUG: Document preservation failed: {e}")
                
                return True
                    
        except Exception as e:
            print(f"Error visualizing DFM issues: {str(e)}")
            traceback.print_exc()
            return False
    
    def _remove_existing_dfm_visualization(self, doc):
        """Remove any existing DFM visualization objects"""
        try:
            # Find and remove existing DFM issue group
            for obj in doc.Objects:
                if obj.Name == "DFM_Issues" and obj.TypeId == "App::DocumentObjectGroup":
                    doc.removeObject(obj.Name)
                    break
        except Exception as e:
            print(f"Error removing existing DFM visualization: {str(e)}")
    
    def _get_actual_mesh_bounding_box(self, doc):
        """Get the bounding box of mesh objects (like your CAD model)"""
        try:
            # Find mesh objects first (like your uploaded CAD model)
            for obj in doc.Objects:
                if hasattr(obj, "Mesh") and hasattr(obj.ViewObject, "Visibility") and obj.ViewObject.Visibility:
                    bbox = obj.Mesh.BoundBox
                    print(f"DEBUG: Found mesh object '{obj.Label}' with bounding box: ({bbox.XMin:.2f}, {bbox.YMin:.2f}, {bbox.ZMin:.2f}) to ({bbox.XMax:.2f}, {bbox.YMax:.2f}, {bbox.ZMax:.2f})")
                    return (bbox.XMin, bbox.YMin, bbox.ZMin, bbox.XMax, bbox.YMax, bbox.ZMax)
            
            # Fallback to shape objects if no mesh found
            for obj in doc.Objects:
                if hasattr(obj, "Shape") and hasattr(obj.ViewObject, "Visibility") and obj.ViewObject.Visibility:
                    bbox = obj.Shape.BoundBox
                    print(f"DEBUG: Found shape object '{obj.Label}' with bounding box: ({bbox.XMin:.2f}, {bbox.YMin:.2f}, {bbox.ZMin:.2f}) to ({bbox.XMax:.2f}, {bbox.YMax:.2f}, {bbox.ZMax:.2f})")
                    return (bbox.XMin, bbox.YMin, bbox.ZMin, bbox.XMax, bbox.YMax, bbox.ZMax)
            
            print("DEBUG: No mesh or shape objects found, using small default bounding box")
            return (0, 0, 0, 10, 1, 2)  # Small default for your thin part
        except Exception as e:
            print(f"Error getting actual mesh bounding box: {str(e)}")
            return (0, 0, 0, 10, 1, 2)  # Small default for your thin part
    
    def _project_point_to_surface(self, mesh_object, point):
        """
        Project the analysis point to the actual mesh surface using robust mesh intersection.
        This ensures highlights appear ON the geometry, not floating in space.
        """
        try:
            if not hasattr(mesh_object, 'Mesh') or not mesh_object.Mesh:
                print(f"DEBUG: No mesh data available for surface projection")
                return point
                
            mesh_data = mesh_object.Mesh
            fc_point = FreeCAD.Vector(point[0], point[1], point[2])
            
            print(f"DEBUG: Projecting point {point} to mesh surface...")
            
            # METHOD 1: Find nearest point on mesh surface (most reliable)
            try:
                # Use correct FreeCAD mesh API
                nearest_point = mesh_data.nearestPointOnMesh(fc_point)
                if nearest_point and len(nearest_point) >= 3:
                    surface_point = (nearest_point[0], nearest_point[1], nearest_point[2])
                    distance = fc_point.distanceToPoint(FreeCAD.Vector(*surface_point))
                    
                    # Only use if reasonably close (within 50% of model size)
                    bbox = mesh_data.BoundBox
                    max_dimension = max(bbox.XLength, bbox.YLength, bbox.ZLength)
                    if distance < max_dimension * 0.5:
                        print(f"DEBUG: Found nearest surface point {surface_point} (distance: {distance:.2f})")
                        return surface_point
            except Exception as e:
                print(f"DEBUG: Nearest point method failed: {e}")
                
            # METHOD 1B: Alternative nearest point approach
            try:
                # Find closest mesh point by direct distance calculation
                min_distance = float('inf')
                closest_point = None
                
                # Sample mesh points efficiently
                sample_step = max(1, mesh_data.CountPoints // 200)  # Sample up to 200 points
                for i in range(0, mesh_data.CountPoints, sample_step):
                    mesh_point = mesh_data.Points[i]
                    distance = fc_point.distanceToPoint(mesh_point)
                    if distance < min_distance:
                        min_distance = distance
                        closest_point = (mesh_point.x, mesh_point.y, mesh_point.z)
                
                if closest_point and min_distance < float('inf'):
                    print(f"DEBUG: Found closest mesh point {closest_point} (distance: {min_distance:.2f})")
                    return closest_point
                    
            except Exception as e:
                print(f"DEBUG: Alternative nearest point method failed: {e}")
            
            # METHOD 2: Ray casting from multiple strategic directions
            directions_and_origins = [
                # Cast rays from outside the mesh towards the point
                ((point[0], point[1], point[2] + 100), (0, 0, -1)),  # From above
                ((point[0], point[1], point[2] - 100), (0, 0, 1)),   # From below
                ((point[0] + 100, point[1], point[2]), (-1, 0, 0)),  # From right
                ((point[0] - 100, point[1], point[2]), (1, 0, 0)),   # From left
                ((point[0], point[1] + 100, point[2]), (0, -1, 0)),  # From front
                ((point[0], point[1] - 100, point[2]), (0, 1, 0)),   # From back
            ]
            
            closest_distance = float('inf')
            best_surface_point = None
            
            for origin, direction in directions_and_origins:
                try:
                    # Cast ray from outside towards the mesh
                    result = mesh_data.nearestFacetOnRay(origin, direction)
                    if result and len(result) >= 2:
                        intersection_point = result[1]  # Intersection point
                        if len(intersection_point) >= 3:
                            surface_point = (intersection_point[0], intersection_point[1], intersection_point[2])
                            distance = fc_point.distanceToPoint(FreeCAD.Vector(*surface_point))
                            
                            if distance < closest_distance:
                                closest_distance = distance
                                best_surface_point = surface_point
                                print(f"DEBUG: Ray cast hit at {surface_point} (distance: {distance:.2f})")
                except Exception as e:
                    continue
            
            if best_surface_point and closest_distance < float('inf'):
                print(f"DEBUG: Best surface projection: {best_surface_point} (distance: {closest_distance:.2f})")
                return best_surface_point
            
            # METHOD 3: Fallback - find closest mesh point by brute force sampling
            try:
                print(f"DEBUG: Using fallback mesh point sampling...")
                min_distance = float('inf')
                closest_mesh_point = None
                
                # Sample mesh points to find the closest one
                sample_step = max(1, mesh_data.CountPoints // 1000)  # Sample up to 1000 points
                for i in range(0, mesh_data.CountPoints, sample_step):
                    mesh_point = mesh_data.Points[i]
                    distance = fc_point.distanceToPoint(mesh_point)
                    if distance < min_distance:
                        min_distance = distance
                        closest_mesh_point = (mesh_point.x, mesh_point.y, mesh_point.z)
                
                if closest_mesh_point:
                    print(f"DEBUG: Closest mesh point: {closest_mesh_point} (distance: {min_distance:.2f})")
                    return closest_mesh_point
                    
            except Exception as e:
                print(f"DEBUG: Fallback sampling failed: {e}")
            
            # Final fallback: return original point
            print(f"DEBUG: All projection methods failed, using original point {point}")
            return point
            
        except Exception as e:
            print(f"ERROR: Surface projection completely failed: {str(e)}")
            return point

    def _project_point_to_surface_with_normal(self, mesh_object, point):
        """
        Project point to mesh surface and return both surface point and surface normal.
        This enables proper overlay alignment with the mesh geometry.
        """
        try:
            if not hasattr(mesh_object, 'Mesh') or not mesh_object.Mesh:
                print(f"DEBUG: No mesh data for surface normal calculation")
                return point, (0, 0, 1)
                
            mesh_data = mesh_object.Mesh
            fc_point = FreeCAD.Vector(point[0], point[1], point[2])
            
            # Calculate surface point and normal
            try:
                # Use the input point directly as the surface point
                surface_point = point
                fc_surface_point = FreeCAD.Vector(surface_point[0], surface_point[1], surface_point[2])
                print(f"DEBUG: Using input point as surface point: {surface_point}")
            except Exception as surface_calc_error:
                print(f"DEBUG: Error calculating surface point: {surface_calc_error}")
                # Use center of bounding box as fallback
                surface_point = (
                    (mesh_data.BoundBox.XMin + mesh_data.BoundBox.XMax) / 2,
                    (mesh_data.BoundBox.YMin + mesh_data.BoundBox.YMax) / 2,
                    (mesh_data.BoundBox.ZMin + mesh_data.BoundBox.ZMax) / 2
                )
                fc_surface_point = FreeCAD.Vector(surface_point[0], surface_point[1], surface_point[2])
                
            except Exception as surface_calc_error:
                print(f"DEBUG: Error calculating surface point: {surface_calc_error}")
                # Use center of bounding box as fallback
                surface_point = (
                    (mesh_data.BoundBox.XMin + mesh_data.BoundBox.XMax) / 2,
                    (mesh_data.BoundBox.YMin + mesh_data.BoundBox.YMax) / 2,
                    (mesh_data.BoundBox.ZMin + mesh_data.BoundBox.ZMax) / 2
                )
                fc_surface_point = FreeCAD.Vector(surface_point[0], surface_point[1], surface_point[2])
            
            # Find surface normal at the calculated point
            surface_normal = (0, 0, 1)  # Default upward normal
            
            try:
                # Find the closest facet to the surface point
                min_distance = float('inf')
                closest_facet = None
                
                print(f"DEBUG: Searching through {mesh_data.CountFacets} facets for closest to point {fc_surface_point}")
                
                # Sample facets to find the closest one (for performance)
                sample_step = max(1, mesh_data.CountFacets // 100)  # Sample more facets for better accuracy
                facets_checked = 0
                
                for i in range(0, mesh_data.CountFacets, sample_step):
                    try:
                        facet = mesh_data.Facets[i]
                        facets_checked += 1
                        
                        # Get facet vertices - Points are tuples (x,y,z), not Vector objects
                        p1, p2, p3 = facet.Points
                        facet_center = FreeCAD.Vector(
                            (p1[0] + p2[0] + p3[0]) / 3,  # x coordinates
                            (p1[1] + p2[1] + p3[1]) / 3,  # y coordinates
                            (p1[2] + p2[2] + p3[2]) / 3   # z coordinates
                        )
                        distance = fc_surface_point.distanceToPoint(facet_center)
                        
                        if distance < min_distance:
                            min_distance = distance
                            closest_facet = facet
                            
                    except Exception as facet_error:
                        print(f"DEBUG: Error processing facet {i}: {facet_error}")
                        continue
                
                print(f"DEBUG: Checked {facets_checked} facets, min distance: {min_distance:.3f}")
                
                if closest_facet and min_distance < 50.0:  # Only use if reasonably close
                    try:
                        normal = closest_facet.Normal
                        surface_normal = (normal.x, normal.y, normal.z)
                        print(f"DEBUG: Found surface normal: {surface_normal} at facet distance {min_distance:.2f}")
                    except Exception as normal_error:
                        print(f"DEBUG: Error getting facet normal: {normal_error}")
                        surface_normal = (0, 0, 1)
                else:
                    print(f"DEBUG: No suitable facet found (distance: {min_distance:.3f}), using default normal")
                    
            except Exception as e:
                print(f"DEBUG: Surface normal calculation failed: {e}")
            
            return surface_point, surface_normal
            
        except Exception as e:
            print(f"ERROR: Surface projection with normal failed: {str(e)}")
            return point, (0, 0, 1)

    def _get_mesh_object(self, doc):
        """Get the mesh object from the document with improved detection"""
        try:
            mesh_objects = []
            
            # Look for mesh objects with different criteria
            for obj in doc.Objects:
                # Check for Mesh objects (STL, OBJ imports)
                if hasattr(obj, "Mesh") and obj.Mesh and obj.Mesh.CountFacets > 0:
                    mesh_objects.append(obj)
                    print(f"DEBUG: Found mesh object: {obj.Name} ({obj.Mesh.CountFacets} facets)")
                
                # Check for Part objects with Shape (native CAD)
                elif hasattr(obj, "Shape") and obj.Shape and hasattr(obj.Shape, "Faces") and len(obj.Shape.Faces) > 0:
                    # Convert Part to mesh for consistent processing
                    try:
                        import MeshPart
                        mesh_obj = MeshPart.meshFromShape(obj.Shape, LinearDeflection=0.1, AngularDeflection=0.1)
                        if mesh_obj and mesh_obj.CountFacets > 0:
                            # Create a temporary mesh object for processing
                            temp_mesh = doc.addObject("Mesh::Feature", f"TempMesh_{obj.Name}")
                            temp_mesh.Mesh = mesh_obj
                            mesh_objects.append(temp_mesh)
                            print(f"DEBUG: Converted Part object to mesh: {obj.Name} -> {temp_mesh.Name} ({mesh_obj.CountFacets} facets)")
                    except Exception as e:
                        print(f"DEBUG: Could not convert Part {obj.Name} to mesh: {e}")
            
            if mesh_objects:
                # Prefer visible objects
                for obj in mesh_objects:
                    if hasattr(obj, "ViewObject") and hasattr(obj.ViewObject, "Visibility"):
                        if obj.ViewObject.Visibility:
                            print(f"DEBUG: Using visible mesh object: {obj.Name}")
                            return obj
                
                # If no visible objects, use the first one
                print(f"DEBUG: Using first available mesh object: {mesh_objects[0].Name}")
                return mesh_objects[0]
            
            print(f"DEBUG: No mesh objects found in document")
            return None
            
        except Exception as e:
            print(f"ERROR: Failed to get mesh object: {str(e)}")
            return None

    def _create_surface_overlay(self, doc, highlight_name, x, y, z, surface_normal, highlight_color, issue_type):
        """Create a surface-aligned overlay as fallback when face-level highlighting fails"""
        try:
            print(f"DEBUG: Creating surface overlay fallback at ({x:.2f}, {y:.2f}, {z:.2f})")
            
            # Create a highly selectable surface-aligned overlay based on issue type
            if 'thin_wall' in issue_type.lower():
                # Rectangular overlay for wall issues - made much more prominent for selection
                overlay = doc.addObject("Part::Box", highlight_name)
                overlay.Length = 5.0  # 5mm length (much larger for better selection)
                overlay.Width = 5.0   # 5mm width (much larger for better selection)
                overlay.Height = 1.0  # Much thicker (1.0mm) for reliable selection
            else:
                # Disc overlay for other issues - made much more prominent for selection
                overlay = doc.addObject("Part::Cylinder", highlight_name)
                overlay.Radius = 2.5   # 2.5mm radius (much larger for better selection)
                overlay.Height = 1.0   # Much thicker (1.0mm) for reliable selection
            
            # Position with much larger surface normal offset for reliable selection
            normal_x, normal_y, normal_z = surface_normal
            offset_distance = 1.0  # Much larger offset for reliable selection (1.0mm)
            
            overlay_center = FreeCAD.Vector(
                x + (normal_x * offset_distance),
                y + (normal_y * offset_distance), 
                z + (normal_z * offset_distance)
            )
            
            # Calculate rotation to align with surface
            try:
                normal_vector = FreeCAD.Vector(normal_x, normal_y, normal_z)
                up_vector = FreeCAD.Vector(0, 0, 1)
                
                if normal_vector.dot(up_vector) < 0.9:
                    rotation_axis = up_vector.cross(normal_vector)
                    if rotation_axis.Length > 0.01:
                        rotation_axis.normalize()
                        angle = math.acos(max(-1, min(1, up_vector.dot(normal_vector))))
                        surface_rotation = FreeCAD.Rotation(rotation_axis, math.degrees(angle))
                    else:
                        surface_rotation = FreeCAD.Rotation(0, 0, 0)
                else:
                    surface_rotation = FreeCAD.Rotation(0, 0, 0)
            except:
                surface_rotation = FreeCAD.Rotation(0, 0, 0)
            
            # Apply placement and color
            overlay.Placement = FreeCAD.Placement(overlay_center, surface_rotation)
            
            if hasattr(overlay, 'ViewObject'):
                overlay.ViewObject.ShapeColor = highlight_color
                overlay.ViewObject.Transparency = 20  # Less transparent for better visibility and selection
                overlay.ViewObject.Selectable = True  # Ensure the overlay is selectable
                overlay.ViewObject.DisplayMode = "Shaded"  # Use shaded mode for better visibility
                # Make the overlay stand out more for selection
                overlay.ViewObject.LineWidth = 2.0
                overlay.ViewObject.PointSize = 3.0
            
            print(f"DEBUG: Created surface overlay fallback with {highlight_color} color")
            return overlay
            
        except Exception as overlay_error:
            print(f"DEBUG: Surface overlay creation failed: {overlay_error}")
            # Ultimate fallback: simple sphere
            sphere = doc.addObject("Part::Sphere", highlight_name)
            sphere.Radius = 0.3
            sphere.Placement = FreeCAD.Placement(FreeCAD.Vector(x, y, z), FreeCAD.Rotation())
            return sphere

    def _group_nearby_issues(self, issues, model_width):
        """Smart grouping to reduce overlapping rectangles and improve visualization clarity"""
        try:
            # Group issues by type and proximity to reduce overlap
            grouped = []
            used_indices = set()
            
            # Define grouping distance (10% of model width)
            group_distance = model_width * 0.1
            
            for i, issue in enumerate(issues):
                if i in used_indices:
                    continue
                    
                # Start a new group with this issue as primary
                group = {
                    'primary_issue': issue,
                    'issues': [issue],
                    'type': issue.get('type', 'general'),
                    'severity': issue.get('severity', 'medium')
                }
                used_indices.add(i)
                
                # Find nearby issues of the same type to group together
                if 'position' in issue and issue['position']:
                    primary_x, primary_y, primary_z = issue['position']
                    
                    for j, other_issue in enumerate(issues):
                        if j in used_indices or j <= i:
                            continue
                            
                        # Only group issues of the same type
                        if other_issue.get('type', 'general') != group['type']:
                            continue
                            
                        if 'position' in other_issue and other_issue['position']:
                            other_x, other_y, other_z = other_issue['position']
                            
                            # Calculate distance
                            distance = ((primary_x - other_x)**2 + (primary_y - other_y)**2 + (primary_z - other_z)**2)**0.5
                            
                            # Group if within distance threshold
                            if distance < group_distance:
                                group['issues'].append(other_issue)
                                used_indices.add(j)
                                
                                # Update severity to highest in group
                                if other_issue.get('severity') == 'critical' or group['severity'] != 'critical':
                                    if other_issue.get('severity') == 'critical':
                                        group['severity'] = 'critical'
                                    elif other_issue.get('severity') == 'high' and group['severity'] not in ['critical']:
                                        group['severity'] = 'high'
                
                grouped.append(group)
            
            # Further reduce by limiting to most critical issues per type
            final_groups = []
            type_counts = {}
            
            # Sort by severity (critical first)
            severity_order = {'critical': 0, 'high': 1, 'medium': 2, 'low': 3}
            grouped.sort(key=lambda g: (severity_order.get(g['severity'], 4), g['type']))
            
            for group in grouped:
                issue_type = group['type']
                
                # Limit thin_wall issues to 5 most critical
                if issue_type == 'thin_wall':
                    if type_counts.get(issue_type, 0) < 5:
                        final_groups.append(group)
                        type_counts[issue_type] = type_counts.get(issue_type, 0) + 1
                # Keep all other issue types
                else:
                    final_groups.append(group)
            
            return final_groups
            
        except Exception as e:
            print(f"Error in smart grouping: {str(e)}")
            # Fallback: return individual issues as single-item groups
            return [{'primary_issue': issue, 'issues': [issue], 'type': issue.get('type', 'general'), 'severity': issue.get('severity', 'medium')} for issue in issues[:10]]  # Limit to 10
    
    def _analyze_issue_position(self, issue, bbox, doc):
        """Analyze CAD structure to determine accurate position for manufacturing issue"""
        try:
            # Extract issue information
            description = issue.get('description', '').lower()
            title = issue.get('title', '').lower()
            severity = issue.get('severity', 'medium')
            
            # CAD dimensions
            x_min, y_min, z_min, x_max, y_max, z_max = bbox
            width = x_max - x_min
            depth = y_max - y_min
            height = z_max - z_min
            center_x = x_min + width / 2
            center_y = y_min + depth / 2
            center_z = z_min + height / 2
            
            print(f"DEBUG: Analyzing issue: '{title}' - '{description[:50]}...'")
            
            # APPROACH 2: Smart CAD Structure Analysis - FIXED KEYWORD MATCHING
            # Map issue types to likely geometric locations with PRIORITY-BASED classification
            
            # PRIORITY 1: GATE PLACEMENT ISSUES (most specific) - IMPROVED DETECTION
            if any(keyword in description.lower() or keyword in title.lower() for keyword in 
                   ['gate placement', 'gate locations', 'gate positioning', 'limited gate', 'gate options']):
                # Position at base center for gate placement
                x = center_x
                y = center_y
                z = z_min + height * 0.1  # Near bottom for gate issues
                print(f"DEBUG: Gate placement issue - positioned at base center")
                return (x, y, z)
            
            # PRIORITY 1B: FLOW/FILLING ISSUES (different from gate placement)
            elif any(keyword in description.lower() or keyword in title.lower() for keyword in 
                     ['flow', 'filling', 'material flow']):
                # Position at end sections where flow issues occur
                x = x_max - width * 0.2  # Near end of part
                y = center_y
                z = center_z  # Middle height for flow issues
                print(f"DEBUG: Flow/filling issue - positioned at end section")
                return (x, y, z)
            
            # PRIORITY 2A: EJECTION ISSUES (specific positioning) - IMPROVED DETECTION
            elif any(keyword in description.lower() or keyword in title.lower() for keyword in 
                     ['ejection', 'ejector', 'ejector pin', 'insufficient ejection', 'ejection area']):
                # Position on main body surfaces where ejector pins would be
                x = center_x - width * 0.2  # Offset from center for ejector area
                y = center_y
                z = center_z + height * 0.1  # Upper-middle for ejector pins
                print(f"DEBUG: Ejection issue - positioned on ejector surface")
                return (x, y, z)
            
            # PRIORITY 2B: DRAFT ANGLE ISSUES (check before general wall issues)
            elif any(keyword in description or keyword in title for keyword in 
                     ['draft', 'angle', 'vertical']):
                # Position on vertical walls (side areas)
                x = x_min + width * 0.2  # Side wall area
                y = center_y
                z = center_z + height * 0.2  # Upper portion of walls
                print(f"DEBUG: Draft angle issue - positioned on vertical surface")
                return (x, y, z)
            
            # PRIORITY 3: COOLING/RATIO ISSUES (check before thickness issues)
            elif any(keyword in description or keyword in title for keyword in 
                     ['cooling', 'ratio', 'warpage', 'uneven', 'length-to-thickness']):
                # Position on center areas where cooling issues occur
                x = center_x
                y = center_y
                z = z_min + height * 0.3  # Lower-middle for cooling issues
                print(f"DEBUG: Cooling/ratio issue - positioned on center section")
                return (x, y, z)
            
            # PRIORITY 4: THREAD/UNDERCUT ISSUES
            elif any(keyword in description or keyword in title for keyword in 
                     ['thread', 'undercut', 'neck', 'cap', 'screw', 'overhang']):
                # Position at top/neck area where threads typically are
                x = center_x
                y = center_y
                z = z_max - height * 0.15  # Near top for thread issues
                print(f"DEBUG: Thread/undercut issue - positioned at neck/top area")
                return (x, y, z)
            
            # PRIORITY 5: SHARP CORNER ISSUES
            elif any(keyword in description or keyword in title for keyword in 
                     ['sharp', 'corner', 'edge', 'radius', 'fillet']):
                # Position at corner/edge areas
                x = x_min + width * 0.1  # Near corner
                y = y_min + depth * 0.1
                z = center_z
                print(f"DEBUG: Sharp corner issue - positioned at edge/corner")
                return (x, y, z)
            
            # PRIORITY 6: WALL THICKNESS ISSUES - MESH-AWARE POSITIONING
            elif any(keyword in description.lower() or keyword in title.lower() for keyword in 
                     ['wall thickness', 'thin wall', 'thick wall', 'minimum wall', 'extremely thin']):
                # Find the actual thinnest section of the mesh
                thin_pos = self._find_thinnest_mesh_section(doc, bbox)
                if thin_pos:
                    print(f"DEBUG: Wall thickness issue - positioned at actual thin section: {thin_pos}")
                    return thin_pos
                # Fallback to geometric calculation
                x = center_x  # Center for thin wall issues
                y = center_y
                z = center_z  # Middle height for visibility
                print(f"DEBUG: Wall thickness issue - positioned at center (fallback)")
                return (x, y, z)
            
            # PRIORITY 7: SURFACE FINISH ISSUES
            elif any(keyword in description or keyword in title for keyword in 
                     ['surface', 'finish', 'texture', 'smooth', 'rough']):
                # Position on main visible surface
                x = center_x + width * 0.2
                y = center_y + depth * 0.2
                z = center_z + height * 0.1
                print(f"DEBUG: Surface finish issue - positioned on visible surface")
                return (x, y, z)
            
            # PRIORITY 8: STRUCTURAL/STRENGTH ISSUES
            elif any(keyword in description or keyword in title for keyword in 
                     ['strength', 'stress', 'weak', 'break', 'structural', 'support']):
                # Position on potential stress concentration areas
                x = center_x
                y = center_y + depth * 0.3
                z = center_z - height * 0.2  # Lower area for structural issues
                print(f"DEBUG: Structural issue - positioned on stress area")
                return (x, y, z)
            
            # 9. SEVERITY-BASED FALLBACK POSITIONING
            else:
                print(f"DEBUG: Using severity-based fallback positioning")
                if severity == 'critical' or severity == 'high':
                    # Critical issues - position prominently (front-center)
                    x = center_x
                    y = y_max - depth * 0.1  # Front of model
                    z = center_z + height * 0.2
                elif severity == 'medium':
                    # Medium issues - position on side
                    x = x_max - width * 0.1  # Right side
                    y = center_y
                    z = center_z
                else:
                    # Low severity - position at top
                    x = center_x
                    y = center_y
                    z = z_max - height * 0.1  # Top area
                
                return (x, y, z)
                
        except Exception as e:
            print(f"ERROR: Failed to analyze issue position: {str(e)}")
            # Emergency fallback to center
            center_x = bbox[0] + (bbox[3] - bbox[0]) / 2
            center_y = bbox[1] + (bbox[4] - bbox[1]) / 2
            center_z = bbox[2] + (bbox[5] - bbox[2]) / 2
            return (center_x, center_y, center_z)
    
    def _find_thinnest_mesh_section(self, doc, bbox):
        """Find the actual thinnest section of the mesh using FreeCAD's native analysis"""
        try:
            print(f"DEBUG: Starting advanced mesh analysis...")
            
            # Find the mesh object
            mesh_obj = None
            for obj in doc.Objects:
                if hasattr(obj, 'Mesh') and obj.Mesh.CountFacets > 0:
                    mesh_obj = obj
                    break
            
            if not mesh_obj:
                print(f"DEBUG: No mesh object found")
                return None
            
            mesh = mesh_obj.Mesh
            x_min, y_min, z_min, x_max, y_max, z_max = bbox
            width = x_max - x_min
            depth = y_max - y_min
            height = z_max - z_min
            
            print(f"DEBUG: Mesh has {mesh.CountFacets} facets, {mesh.CountPoints} points")
            print(f"DEBUG: Analyzing bounding box: ({x_min:.2f}, {y_min:.2f}, {z_min:.2f}) to ({x_max:.2f}, {y_max:.2f}, {z_max:.2f})")
            
            # COMPREHENSIVE GEOMETRIC ANALYSIS
            all_issues = []
            
            # 1. THIN WALL DETECTION - Cross-sectional analysis
            print(f"DEBUG: Analyzing thin walls...")
            num_samples = 25  # High resolution sampling
            for i in range(num_samples):
                x_sample = x_min + (width * i / (num_samples - 1))
                
                # Find all mesh points near this X coordinate
                nearby_points = []
                tolerance = width * 0.04  # 4% tolerance for precision
                
                for point in mesh.Points:
                    if abs(point.x - x_sample) <= tolerance:
                        nearby_points.append(point)
                
                if len(nearby_points) >= 4:
                    # Calculate local thickness (Y-direction for clamp)
                    y_coords = [p.y for p in nearby_points]
                    z_coords = [p.z for p in nearby_points]
                    
                    local_thickness = max(y_coords) - min(y_coords)
                    
                    # Identify thin sections (< 1.5mm = problematic for injection molding)
                    if local_thickness < 1.5:
                        center_y = (max(y_coords) + min(y_coords)) / 2
                        center_z = (max(z_coords) + min(z_coords)) / 2
                        
                        # More nuanced severity assignment for better color distribution
                        if local_thickness < 0.6:
                            severity = 'critical'  # Red - extremely thin walls
                        elif local_thickness < 1.0:
                            severity = 'high'      # Orange - thin walls
                        elif local_thickness < 1.5:
                            severity = 'medium'    # Yellow - borderline walls
                        else:
                            severity = 'low'       # Blue - acceptable walls
                        
                        all_issues.append({
                            'position': (x_sample, center_y, center_z),
                            'thickness': local_thickness,
                            'type': 'thin_wall',
                            'severity': severity,
                            'description': f'Thin wall: {local_thickness:.2f}mm (min recommended: 1.2mm)'
                        })
                        
                        print(f"DEBUG: Thin wall at X={x_sample:.2f}, thickness={local_thickness:.2f}mm, severity={severity}")
            
            # 2. SHARP CORNER DETECTION - Curvature analysis
            print(f"DEBUG: Analyzing sharp corners...")
            try:
                # Analyze mesh facets for sharp angles
                sharp_corners = []
                for i, facet in enumerate(mesh.Facets):
                    if i % 50 == 0:  # Sample every 50th facet for performance
                        # Get facet normal and adjacent facets
                        normal = facet.Normal
                        
                        # Check for sharp transitions (simplified approach)
                        # In a real implementation, you'd check adjacent facet angles
                        if abs(normal.z) < 0.3:  # Steep angle indicator
                            center = facet.Center
                            # Vary severity based on angle steepness for better color distribution
                            if abs(normal.z) < 0.1:
                                severity = 'critical'  # Red - very sharp corners
                            elif abs(normal.z) < 0.2:
                                severity = 'high'      # Orange - sharp corners
                            else:
                                severity = 'medium'    # Yellow - moderate corners
                            
                            sharp_corners.append({
                                'position': (center.x, center.y, center.z),
                                'type': 'sharp_corner',
                                'severity': severity,
                                'description': f'Sharp corner detected (angle severity: {severity})'
                            })
                
                if sharp_corners:
                    # Take the most prominent sharp corner
                    all_issues.extend(sharp_corners[:2])  # Limit to 2 for clarity
                    print(f"DEBUG: Found {len(sharp_corners)} sharp corners")
                    
            except Exception as e:
                print(f"DEBUG: Sharp corner analysis failed: {e}")
            
            # 3. UNDERCUT DETECTION - Overhang analysis
            print(f"DEBUG: Analyzing undercuts...")
            try:
                undercuts = []
                # Sample Z-levels to find overhangs
                for z_level in [z_min + height * 0.3, z_min + height * 0.7]:
                    points_at_level = [p for p in mesh.Points if abs(p.z - z_level) < height * 0.1]
                    
                    if len(points_at_level) > 10:
                        x_coords = [p.x for p in points_at_level]
                        y_coords = [p.y for p in points_at_level]
                        
                        # Check for overhangs (simplified)
                        x_range = max(x_coords) - min(x_coords)
                        if x_range > width * 0.5:  # Potential overhang
                            center_x_level = (max(x_coords) + min(x_coords)) / 2
                            center_y_level = (max(y_coords) + min(y_coords)) / 2
                            
                            # Vary severity based on overhang extent for better color distribution
                            overhang_ratio = x_range / width
                            if overhang_ratio > 0.9:
                                severity = 'critical'  # Red - severe undercuts
                            elif overhang_ratio > 0.8:
                                severity = 'high'      # Orange - significant undercuts
                            elif overhang_ratio > 0.6:
                                severity = 'medium'    # Yellow - moderate undercuts
                            else:
                                severity = 'low'       # Blue - minor undercuts
                            
                            undercuts.append({
                                'position': (center_x_level, center_y_level, z_level),
                                'type': 'undercut',
                                'severity': severity,
                                'description': f'Undercut/overhang at Z={z_level:.2f}mm (extent: {overhang_ratio:.1%})'
                            })
                
                if undercuts:
                    all_issues.extend(undercuts[:1])  # Limit to 1 for clarity
                    print(f"DEBUG: Found {len(undercuts)} potential undercuts")
                    
            except Exception as e:
                print(f"DEBUG: Undercut analysis failed: {e}")
            
            # 4. ASPECT RATIO ISSUES - Length/width ratio
            print(f"DEBUG: Analyzing aspect ratio...")
            # Calculate center coordinates
            center_x = x_min + width / 2
            center_y = y_min + depth / 2
            center_z = z_min + height / 2
            
            aspect_ratio = width / depth if depth > 0 else 0
            if aspect_ratio > 8 or aspect_ratio < 0.125:  # Very long/thin or very wide/thin
                all_issues.append({
                    'position': (center_x, center_y, center_z),
                    'type': 'aspect_ratio',
                    'severity': 'medium',
                    'description': f'Poor aspect ratio: {aspect_ratio:.1f}:1 (recommended: 2:1 to 4:1)'
                })
                print(f"DEBUG: Poor aspect ratio: {aspect_ratio:.1f}:1")
            
            # 5. DRAFT ANGLE ISSUES - Mold release analysis
            print(f"DEBUG: Analyzing draft angles...")
            try:
                # Simplified draft angle analysis for vertical surfaces
                if height > width * 0.5:  # Tall parts need draft angles
                    all_issues.append({
                        'position': (center_x, center_y, z_min + height * 0.8),  # Top area
                        'type': 'draft_angle',
                        'severity': 'high',
                        'description': 'Vertical surfaces need 1-3° draft angle for mold release'
                    })
                    print(f"DEBUG: Draft angle issue detected for tall part (H:{height:.1f}mm)")
            except Exception as e:
                print(f"DEBUG: Draft angle analysis failed: {e}")
            
            # 6. SINK MARK ANALYSIS - Thick sections
            print(f"DEBUG: Analyzing sink marks...")
            try:
                # Check for thick sections that may cause sink marks
                max_thickness = max([issue.get('thickness', 0) for issue in all_issues if issue.get('type') == 'thin_wall'] + [1.5])
                if max_thickness > 4.0:  # Thick sections > 4mm
                    all_issues.append({
                        'position': (center_x, center_y, center_z),
                        'type': 'sink_mark',
                        'severity': 'medium',
                        'description': f'Thick sections ({max_thickness:.1f}mm) may cause sink marks'
                    })
                    print(f"DEBUG: Sink mark risk detected - thickness: {max_thickness:.1f}mm")
            except Exception as e:
                print(f"DEBUG: Sink mark analysis failed: {e}")
            
            # 7. WARPAGE ANALYSIS - Asymmetric geometry
            print(f"DEBUG: Analyzing warpage risk...")
            try:
                # Check for asymmetric cooling (simplified)
                thickness_variation = len([i for i in all_issues if i.get('type') == 'thin_wall'])
                if thickness_variation > 5:  # Many thickness variations
                    all_issues.append({
                        'position': (center_x, center_y, center_z),
                        'type': 'warpage',
                        'severity': 'medium',
                        'description': f'High thickness variation ({thickness_variation} areas) increases warpage risk'
                    })
                    print(f"DEBUG: Warpage risk detected - {thickness_variation} thickness variations")
            except Exception as e:
                print(f"DEBUG: Warpage analysis failed: {e}")
            
            # 8. FLOW LENGTH ANALYSIS - Material flow distance
            print(f"DEBUG: Analyzing flow length...")
            try:
                flow_length = max(width, depth)  # Longest flow path
                if flow_length > 100:  # Long flow path
                    all_issues.append({
                        'position': (x_min + width * 0.9, center_y, center_z),  # Far end
                        'type': 'flow_length',
                        'severity': 'medium',
                        'description': f'Long flow path ({flow_length:.1f}mm) may cause flow lines'
                    })
                    print(f"DEBUG: Long flow path detected: {flow_length:.1f}mm")
            except Exception as e:
                print(f"DEBUG: Flow length analysis failed: {e}")
            
            # 9. GATE PLACEMENT ANALYSIS - Injection point optimization
            print(f"DEBUG: Analyzing gate placement...")
            try:
                # Recommend gate placement for clamp geometry
                if width > depth * 2:  # Long thin part
                    all_issues.append({
                        'position': (center_x, y_min, center_z),  # Side gate
                        'type': 'gate_placement',
                        'severity': 'low',
                        'description': 'Consider side gate placement for uniform filling'
                    })
                    print(f"DEBUG: Gate placement recommendation for long part")
                
                # Add additional gate placement recommendations with varied severities
                if volume > 50000:  # Large parts need multiple gates
                    all_issues.append({
                        'position': (x_min + width * 0.25, center_y, center_z),
                        'type': 'gate_placement',
                        'severity': 'medium',
                        'description': 'Large part may require multiple gate locations'
                    })
                    all_issues.append({
                        'position': (x_min + width * 0.75, center_y, center_z),
                        'type': 'gate_placement', 
                        'severity': 'low',
                        'description': 'Secondary gate location for balanced filling'
                    })
            except Exception as e:
                print(f"DEBUG: Gate placement analysis failed: {e}")
            
            # 10. SURFACE FINISH ANALYSIS - Add critical surface finish issues
            print(f"DEBUG: Analyzing surface finish requirements...")
            try:
                # Critical surface finish areas (high visibility surfaces)
                all_issues.append({
                    'position': (center_x, y_max, z_max - height * 0.1),  # Top front surface
                    'type': 'surface_finish',
                    'severity': 'critical',
                    'description': 'Critical surface finish area - high visibility'
                })
                
                # High priority surface areas
                all_issues.append({
                    'position': (x_max - width * 0.1, center_y, center_z),  # Side surface
                    'type': 'surface_finish',
                    'severity': 'high',
                    'description': 'High priority surface finish - visible edge'
                })
                
                print(f"DEBUG: Added surface finish analysis points")
            except Exception as e:
                print(f"DEBUG: Surface finish analysis failed: {e}")
            
            # 11. COOLING ANALYSIS - Add cooling-related issues
            print(f"DEBUG: Analyzing cooling requirements...")
            try:
                # Hot spots that need cooling attention
                if volume > 30000:  # Larger parts have cooling challenges
                    all_issues.append({
                        'position': (center_x, center_y, center_z),  # Center mass
                        'type': 'cooling',
                        'severity': 'critical',
                        'description': 'Large mass center requires enhanced cooling'
                    })
                
                # Cooling channel recommendations
                all_issues.append({
                    'position': (center_x, y_min + depth * 0.2, center_z),
                    'type': 'cooling',
                    'severity': 'low',
                    'description': 'Recommended cooling channel location'
                })
                
                print(f"DEBUG: Added cooling analysis points")
            except Exception as e:
                print(f"DEBUG: Cooling analysis failed: {e}")
            
            # Return the most critical issue found
            if all_issues:
                # Sort by severity: critical > high > medium
                severity_order = {'critical': 0, 'high': 1, 'medium': 2}
                all_issues.sort(key=lambda x: severity_order.get(x['severity'], 3))
                
                most_critical = all_issues[0]
                print(f"DEBUG: Most critical issue: {most_critical['type']} - {most_critical['description']}")
                print(f"DEBUG: Total geometric issues found: {len(all_issues)}")
                
                # Store all issues for comprehensive reporting
                self.detected_geometric_issues = all_issues
                
                return most_critical['position']
            
            print(f"DEBUG: No specific geometric issues found")
            return None
            
        except Exception as e:
            print(f"ERROR: Mesh analysis failed: {str(e)}")
            return None
    
    def _perform_comprehensive_geometric_analysis(self):
        """Perform comprehensive geometric analysis and return detected issues"""
        try:
            print("🔍 Starting comprehensive geometric analysis...")
            
            # Get active document
            doc = FreeCAD.ActiveDocument
            if not doc:
                print("No active document for geometric analysis")
                return []
            
            # Find the mesh or solid object
            target_obj = None
            for obj in doc.Objects:
                if hasattr(obj, 'Mesh') and obj.Mesh.CountFacets > 0:
                    target_obj = obj
                    break
                elif hasattr(obj, 'Shape') and obj.Shape.Volume > 0:
                    target_obj = obj
                    break
            
            if not target_obj:
                print("No suitable object found for geometric analysis")
                return []
            
            # Get bounding box
            if hasattr(target_obj, 'Mesh'):
                bbox = target_obj.Mesh.BoundBox
            else:
                bbox = target_obj.Shape.BoundBox
            
            bbox_tuple = (bbox.XMin, bbox.YMin, bbox.ZMin, bbox.XMax, bbox.YMax, bbox.ZMax)
            
            # Use the existing comprehensive analysis logic
            position = self._find_thinnest_mesh_section(doc, bbox_tuple)
            
            # Return the stored geometric issues if available
            if hasattr(self, 'detected_geometric_issues') and self.detected_geometric_issues:
                print(f"🎯 Returning {len(self.detected_geometric_issues)} detected geometric issues")
                return self.detected_geometric_issues
            else:
                print("⚠️ No geometric issues detected by analysis")
                return []
                
        except Exception as e:
            print(f"ERROR: Comprehensive geometric analysis failed: {str(e)}")
            return []
    
    def _create_geometric_dfm_result(self, cloud_result, geometric_issues, manufacturing_process, material, production_volume):
        """Create DFM result with geometric analysis findings"""
        try:
            print(f"🔧 Creating DFM result with {len(geometric_issues)} geometric issues...")
            
            # Start with the cloud result structure
            result = cloud_result.copy() if cloud_result else {}
            data = result.get('data', {})
            
            # Convert geometric issues to DFM format
            dfm_issues = []
            for issue in geometric_issues:
                dfm_issue = {
                    'title': issue.get('type', 'Manufacturing Issue').replace('_', ' ').title(),
                    'description': issue.get('description', 'Geometric issue detected'),
                    'severity': issue.get('severity', 'medium'),
                    'position': issue.get('position', (0, 0, 0)),
                    'type': issue.get('type', 'geometric'),
                    'recommendations': self._get_recommendations_for_issue(issue, manufacturing_process)
                }
                dfm_issues.append(dfm_issue)
            
            # Update the result with geometric findings
            data['design_issues'] = dfm_issues
            data['analysis_method'] = 'Comprehensive Geometric Analysis'
            data['issues_found'] = len(dfm_issues)
            
            # Update manufacturability score based on issues
            critical_issues = len([i for i in dfm_issues if i['severity'] == 'critical'])
            high_issues = len([i for i in dfm_issues if i['severity'] == 'high'])
            medium_issues = len([i for i in dfm_issues if i['severity'] == 'medium'])
            
            # Calculate score (start at 100, deduct for issues)
            score = 100 - (critical_issues * 25) - (high_issues * 15) - (medium_issues * 10)
            score = max(score, 20)  # Minimum score of 20
            
            data['manufacturability_score'] = score
            data['overall_rating'] = 'Excellent' if score >= 90 else 'Good' if score >= 70 else 'Fair' if score >= 50 else 'Poor'
            
            result['data'] = data
            result['success'] = True
            
            print(f"[OK] Created geometric DFM result: {len(dfm_issues)} issues, score: {score}/100")
            return result
            
        except Exception as e:
            print(f"ERROR: Failed to create geometric DFM result: {str(e)}")
            return cloud_result if cloud_result else {'success': False, 'error': str(e)}
    
    def _get_recommendations_for_issue(self, issue, manufacturing_process):
        """Get specific recommendations for each type of geometric issue"""
        issue_type = issue.get('type', '')
        process = manufacturing_process.lower()
        
        recommendations = []
        
        if issue_type == 'thin_wall':
            if 'injection' in process:
                recommendations = [
                    "Increase wall thickness to minimum 1.2mm for injection molding",
                    "Add ribs or gussets for structural support",
                    "Consider material with better flow characteristics"
                ]
            elif 'cnc' in process:
                recommendations = [
                    "Increase thickness to avoid tool deflection",
                    "Use shorter, more rigid cutting tools",
                    "Add support structures during machining"
                ]
        elif issue_type == 'sharp_corner':
            recommendations = [
                "Add fillets with minimum 0.5mm radius",
                "Avoid sharp internal corners for stress concentration",
                "Consider draft angles for molding processes"
            ]
        elif issue_type == 'undercut':
            if 'injection' in process:
                recommendations = [
                    "Eliminate undercuts or add side actions",
                    "Redesign geometry for straight pull molding",
                    "Consider split-line placement"
                ]
        elif issue_type == 'aspect_ratio':
            recommendations = [
                "Optimize length-to-width ratio (2:1 to 4:1)",
                "Add ribs to prevent warpage",
                "Consider material shrinkage compensation"
            ]
        elif issue_type == 'draft_angle':
            recommendations = [
                "Add 1-3° draft angle to vertical surfaces",
                "Use tapered walls for easier mold release",
                "Consider split-line placement to minimize draft requirements"
            ]
        elif issue_type == 'sink_mark':
            recommendations = [
                "Reduce wall thickness in thick sections",
                "Add ribs instead of thick walls for strength",
                "Use uniform wall thickness throughout"
            ]
        elif issue_type == 'warpage':
            recommendations = [
                "Maintain uniform wall thickness",
                "Add ribs for structural support",
                "Consider symmetric cooling design"
            ]
        elif issue_type == 'flow_length':
            recommendations = [
                "Consider multiple gate locations",
                "Optimize part orientation in mold",
                "Use materials with better flow properties"
            ]
        elif issue_type == 'gate_placement':
            recommendations = [
                "Position gate for balanced filling",
                "Avoid gate marks in visible areas",
                "Consider hot runner system for multiple gates"
            ]
        else:
            recommendations = ["Review geometry for manufacturability"]
        
        return recommendations
    
    def _get_model_bounding_box(self, doc):
        """Get the bounding box of all visible objects in the document"""
        try:
            # Find all visible shapes
            shapes = []
            for obj in doc.Objects:
                if hasattr(obj, "Shape") and hasattr(obj.ViewObject, "Visibility") and obj.ViewObject.Visibility:
                    shapes.append(obj.Shape)
            
            if not shapes:
                return (-50, -50, -50, 50, 50, 50)  # Default bounding box
            
            # Calculate combined bounding box
            bbox = shapes[0].BoundBox
            for shape in shapes[1:]:
                bbox.add(shape.BoundBox)
            
            return (bbox.XMin, bbox.YMin, bbox.ZMin, bbox.XMax, bbox.YMax, bbox.ZMax)
        except Exception as e:
            print(f"Error getting model bounding box: {str(e)}")
            return (-50, -50, -50, 50, 50, 50)  # Default bounding box
    
    def _get_model_size(self, doc):
        """Get the approximate size of the model"""
        try:
            bbox = self._get_model_bounding_box(doc)
            size_x = bbox[3] - bbox[0]
            size_y = bbox[4] - bbox[1]
            size_z = bbox[5] - bbox[2]
            return max(size_x, size_y, size_z)
        except Exception as e:
            print(f"Error getting model size: {str(e)}")
            return 100  # Default size
    
    def _create_text_label(self, doc, text, position):
        """Create a text label at the specified position"""
        try:
            # Check if Draft workbench is available
            if hasattr(FreeCAD, "getDraftWorkingPlane"):
                import Draft
                label = Draft.makeText([text], point=position)
                return label
            return None
        except Exception as e:
            print(f"Error creating text label: {str(e)}")
            return None
    
    # ========== ROBUST DFM VISUALIZATION SYSTEM ==========
    
    # DFM Visualization Constants
    SEVERITY_STYLE = {
        "critical": {"color": (1.0, 0.0, 0.0),   "transparency": 35},  # #FF0000
        "high":     {"color": (1.0, 0.302, 0.0), "transparency": 35},  # #FF4D00
        "medium":   {"color": (1.0, 0.702, 0.0), "transparency": 30},  # #FFB300
        "low":      {"color": (0.0, 0.5, 1.0),   "transparency": 30},  # #0080FF
    }
    OVERLAY_PART_PREFIX = "DFM_OVERLAYS_FOR_"
    FACET_TEMP_SUFFIX = "_FacetColor"
    
    # Keep track of bases with overlays for auto-sync observer
    _DFM_BASE_REGISTRY = set()
    _DFM_OBSERVER = None
    
    def _V(self, t):
        """Convert tuple to FreeCAD Vector"""
        return FreeCAD.Vector(float(t[0]), float(t[1]), float(t[2]))
    
    def _get_mesh_from_object(self, obj, lin_def=0.1, ang_def=0.5):
        """Get mesh from Mesh::Feature (STL/OBJ) or Part::Feature (STEP/Solid)"""
        if hasattr(obj, "Mesh"):  # STL/OBJ
            return obj.Mesh.copy()
        elif hasattr(obj, "Shape"):  # STEP or any Part::Feature
            import MeshPart
            return MeshPart.meshFromShape(Shape=obj.Shape,
                                          LinearDeflection=float(lin_def),
                                          AngularDeflection=float(ang_def))
        else:
            raise ValueError(f"Object {obj.Name} is not meshable.")
    
    def _build_centers_and_tris(self, mesh):
        """Build facet centers and triangles from mesh"""
        centers, tris = [], []
        for f in mesh.Facets:
            p1, p2, p3 = f.Points
            a, b, c = self._V(p1), self._V(p2), self._V(p3)
            centers.append(FreeCAD.Vector((a.x+b.x+c.x)/3.0, (a.y+b.y+c.y)/3.0, (a.z+b.z+c.z)/3.0))
            tris.append((a,b,c))
        return centers, tris
    
    def _nearest_face_index(self, p, centers):
        """Find nearest face index to point"""
        best_i, best_d2 = -1, 1e100
        for i,c in enumerate(centers):
            d2 = (c - p).Length ** 2
            if d2 < best_d2:
                best_i, best_d2 = i, d2
        return best_i
    
    def _project_point_to_triangle(self, p, a, b, c):
        """Project point to triangle with barycentric clamping"""
        ab, ac = b-a, c-a
        n = ab.cross(ac)
        nn = n.dot(n)
        if nn == 0:  # degenerate
            return min((a,b,c), key=lambda q: (q-p).Length)
        # orthogonal projection
        proj = p - n * ((p - a).dot(n) / nn)
        # barycentric clamp
        v0, v1, v2 = ab, ac, proj - a
        d00, d01, d11 = v0.dot(v0), v0.dot(v1), v1.dot(v1)
        d20, d21 = v2.dot(v0), v2.dot(v1)
        denom = d00*d11 - d01*d01
        if denom == 0:
            return min((a,b,c), key=lambda q: (q-p).Length)
        v = (d11*d20 - d01*d21) / denom
        w = (d00*d21 - d01*d20) / denom
        u = 1.0 - v - w
        u = max(0.0, min(1.0, u))
        v = max(0.0, min(1.0, v))
        if u+v > 1.0:
            s = u+v
            u, v = u/s, v/s
        w = 1.0 - u - v
        return a*u + b*v + c*w
    
    def _faces_within_radius(self, point, centers, r_mm):
        """Find faces within radius of point"""
        r2 = r_mm*r_mm
        return [i for i,c in enumerate(centers) if (c - point).Length**2 <= r2]
    
    def _overlay_part_name(self, base_obj_name):
        """Generate overlay part name"""
        return self.OVERLAY_PART_PREFIX + base_obj_name
    
    def _ensure_overlay_part(self, base_obj):
        """Create or reuse App::Part for overlays tied to base object"""
        doc = FreeCAD.ActiveDocument
        part_name = self._overlay_part_name(base_obj.Name)
        part = doc.getObject(part_name)
        if not part:
            part = doc.addObject("App::Part", part_name)
        # hard-set placement to base
        part.Placement = base_obj.Placement
        return part
    
    def _clear_overlays_for(self, base_obj):
        """Clear overlays for base object"""
        doc = FreeCAD.ActiveDocument
        part = doc.getObject(self._overlay_part_name(base_obj.Name))
        if part:
            # delete children then the part
            for ch in list(part.Group):
                doc.removeObject(ch.Name)
            doc.removeObject(part.Name)
            doc.recompute()
        # also un-register base if present
        if base_obj.Name in self._DFM_BASE_REGISTRY:
            self._DFM_BASE_REGISTRY.discard(base_obj.Name)
    
    def _build_overlay(self, mesh, indices, name, color, transparency, parent_part):
        """Build overlay mesh from indices"""
        if not indices: 
            return None
        import Mesh
        new_mesh = Mesh.Mesh()
        for idx in indices:
            facet = mesh.Facets[int(idx)]
            p1,p2,p3 = facet.Points
            new_mesh.addFacet(self._V(p1), self._V(p2), self._V(p3))
        obj = FreeCAD.ActiveDocument.addObject("Mesh::Feature", name)
        obj.Mesh = new_mesh
        vo = obj.ViewObject
        vo.ShapeColor = color
        vo.Transparency = int(transparency)
        vo.DisplayMode = "Shaded"
        vo.Lighting = "One side"
        # Put overlay under the overlay App::Part so it inherits transform
        parent_part.addObject(obj)
        obj.Placement = FreeCAD.Placement()  # identity; inherits parent transform
        return obj
    
    def _dfm_visualize(self, obj_name, issues, method="overlay", radius_mm=3.0, clear=True, lin_def=0.1, ang_def=0.5):
        """
        Professional DFM visualization with per-issue overlays and 3D tooltips
        obj_name: FreeCAD tree object name (Mesh::Feature or Part::Feature)
        method: "overlay" (recommended) - uses professional per-issue system
        radius_mm: local patch radius around each issue projection (3.0mm default)
        lin_def / ang_def: tessellation quality for STEP (lower = finer)
        """
        # Use the professional DFM overlay system with per-issue tooltips
        return dfm_draw_per_issue_overlays(obj_name, issues, radius_mm, clear, lin_def, ang_def)
    
    def _method2_overlays(self, base_obj, issues, radius_mm=2.5, clear=True, lin_def=0.1, ang_def=0.5):
        """Method 2: Overlay submeshes (preferred)"""
        from collections import defaultdict
        
        if clear: 
            self._clear_overlays_for(base_obj)
        mesh = self._get_mesh_from_object(base_obj, lin_def, ang_def)
        centers, tris = self._build_centers_and_tris(mesh)

        # Create (or reuse) a transform-carrying container (App::Part)
        part = self._ensure_overlay_part(base_obj)

        buckets = defaultdict(set)
        for it in issues:
            pos = it.get("position")
            if not pos or len(pos)!=3: 
                continue
            p = FreeCAD.Vector(float(pos[0]), float(pos[1]), float(pos[2]))
            i0 = self._nearest_face_index(p, centers)
            if i0 < 0: 
                continue
            a,b,c = tris[i0]
            p_proj = self._project_point_to_triangle(p, a, b, c)
            face_ids = self._faces_within_radius(p_proj, centers, radius_mm) or [i0]
            sev = (it.get("severity") or "medium").lower().strip()
            if sev not in self.SEVERITY_STYLE: 
                sev = "medium"
            buckets[sev].update(face_ids)

        created = []
        for sev, idxs in buckets.items():
            style = self.SEVERITY_STYLE[sev]
            overlay = self._build_overlay(mesh, sorted(idxs),
                                         f"DFM_{sev.upper()}_{base_obj.Name}",
                                         style["color"], style["transparency"],
                                         parent_part=part)
            if overlay: 
                created.append(overlay)

        # Register for auto-sync
        self._DFM_BASE_REGISTRY.add(base_obj.Name)
        FreeCAD.ActiveDocument.recompute()
        return created
    
    def _method1_facet_color(self, base_obj, issues, radius_mm=2.5, lin_def=0.1, ang_def=0.5):
        """Method 1: Facet coloring (fallback)"""
        from collections import defaultdict
        
        mesh = self._get_mesh_from_object(base_obj, lin_def, ang_def)
        centers, tris = self._build_centers_and_tris(mesh)
        n = len(centers)
        diffuse = [(0.8,0.8,0.8)] * n
        per_sev = defaultdict(set)
        
        for it in issues:
            pos = it.get("position")
            if not pos or len(pos)!=3: 
                continue
            p = FreeCAD.Vector(float(pos[0]), float(pos[1]), float(pos[2]))
            i0 = self._nearest_face_index(p, centers)
            if i0 < 0: 
                continue
            a,b,c = tris[i0]
            p_proj = self._project_point_to_triangle(p, a, b, c)
            face_ids = self._faces_within_radius(p_proj, centers, radius_mm) or [i0]
            sev = (it.get("severity") or "medium").lower().strip()
            if sev not in self.SEVERITY_STYLE: 
                sev = "medium"
            per_sev[sev].update(face_ids)

        # paint by severity (critical overwrites)
        order = ["low","medium","high","critical"]
        for sev in order:
            if sev not in per_sev: 
                continue
            color = self.SEVERITY_STYLE[sev]["color"]
            for i in per_sev[sev]:
                diffuse[int(i)] = color

        shown_obj_name = None
        if hasattr(base_obj, "Mesh"):
            base_obj.ViewObject.DiffuseColor = diffuse
            base_obj.ViewObject.DisplayMode = "Shaded"
            base_obj.ViewObject.Lighting = "One side"
            base_obj.ViewObject.Transparency = 0
            shown_obj_name = base_obj.Name
        else:
            # STEP: make a display mesh that follows transforms via an App::Part container
            part = self._ensure_overlay_part(base_obj)
            temp = FreeCAD.ActiveDocument.addObject("Mesh::Feature", f"{base_obj.Name}{self.FACET_TEMP_SUFFIX}")
            temp.Mesh = mesh
            temp.ViewObject.DiffuseColor = diffuse
            temp.ViewObject.DisplayMode = "Shaded"
            temp.ViewObject.Lighting = "One side"
            part.addObject(temp)
            temp.Placement = FreeCAD.Placement()  # identity; inherits
            shown_obj_name = temp.Name

        # Register for auto-sync
        self._DFM_BASE_REGISTRY.add(base_obj.Name)
        FreeCAD.ActiveDocument.recompute()
        return shown_obj_name
    
    def toggle_overlays(self, base_obj_name, visible=True):
        """Toggle overlay visibility using professional DFM overlay system"""
        dfm_toggle_overlays(base_obj_name, visible)
    
    def sync_overlay_part_to_base(self, base_obj_name):
        """Manual sync overlay part to base object using professional DFM overlay system"""
        sync_overlay_part_to_base(base_obj_name)
    
    # ========== END ROBUST DFM VISUALIZATION SYSTEM ==========

    def get_cost_analysis(self):
        """Get detailed cost analysis from the DFM service"""
        try:
            if self.cloud_integration and self.last_dfm_result and self.last_dfm_result.get("success", False):
                return self.cloud_integration.get_cost_analysis()
            return None
        except Exception as e:
            print(f"Error getting cost analysis: {str(e)}")
            return None
    
    def get_alternative_processes(self):
        """Get alternative manufacturing processes from the DFM service"""
        try:
            if self.cloud_integration and self.last_dfm_result and self.last_dfm_result.get("success", False):
                return self.cloud_integration.get_alternative_processes()
            return None
        except Exception as e:
            print(f"Error getting alternative processes: {str(e)}")
            return None
    
    def visualize_tool_paths(self):
        """Visualize tool paths in the FreeCAD view"""
        try:
            if self.cloud_integration:
                self.cloud_integration.visualize_tool_paths()
            elif self.last_tool_result and self.last_tool_result.get("success", False):
                # Basic visualization if cloud integration not available
                tool_paths = self.last_tool_result.get("data", {}).get("tool_paths", [])
                if not tool_paths:
                    FreeCAD.Console.PrintMessage("No tool paths to visualize\n")
                    return
                    
                # Create visualization objects
                doc = FreeCAD.ActiveDocument
                if not doc:
                    FreeCAD.Console.PrintError("No active document for visualization\n")
                    return
                    
                # Create a group for tool paths
                path_group = doc.addObject("App::DocumentObjectGroup", "Tool_Paths")
                
                # Add visualization for each tool path
                for i, path in enumerate(tool_paths):
                    points = path.get("points", [])
                    tool_name = path.get("tool_name", f"Tool_{i+1}")
                    
                    if not points or len(points) < 2:
                        continue
                        
                    # Create a polyline for the tool path
                    polyline = []
                    for point in points:
                        polyline.append(FreeCAD.Vector(point[0], point[1], point[2]))
                    
                    # Create a wire from the points
                    wire = Part.makePolygon(polyline)
                    path_obj = doc.addObject("Part::Feature", f"Path_{tool_name}")
                    path_obj.Shape = wire
                    
                    # Set color and line width
                    if hasattr(path_obj, "ViewObject"):
                        path_obj.ViewObject.LineColor = (0.0, 0.0, 1.0)  # Blue
                        path_obj.ViewObject.LineWidth = 2.0
                    
                    # Add to group
                    path_group.addObject(path_obj)
                
                doc.recompute()
                FreeCAD.Console.PrintMessage(f"Visualized {len(tool_paths)} tool paths\n")
        except Exception as e:
            print(f"Error visualizing tool paths: {str(e)}")
            traceback.print_exc()

# Context manager for design context
class DesignContextManager:
    """Manage design context for natural language CAD"""
    
    def __init__(self):
        self.context = {
            'project': 'default',
            'process': 'any',
            'material': 'any',
            'units': 'mm',
            'current_objects': []
        }
    
    def update_context(self, key, value):
        """Update a context value"""
        self.context[key] = value
    
    def get_context(self):
        """Get the current context"""
        return self.context
    
    def add_object(self, obj):
        """Add an object to the current context"""
        if obj not in self.context['current_objects']:
            self.context['current_objects'].append(obj)
    
    def clear_objects(self):
        """Clear the current objects"""
        self.context['current_objects'] = []

# Claude AI processor for conversational CAD generation
class CloudAIProcessor:
    """Process natural language using Claude AI for conversational CAD generation"""
    
    def __init__(self, cloud_client=None):
        self.cloud_client = cloud_client
        self.context_memory = []
        self.anthropic_client = None
        
        # Initialize Claude/Anthropic client for conversational CAD generation
        if ANTHROPIC_AVAILABLE and ANTHROPIC_API_KEY:
            try:
                self.anthropic_client = anthropic.Anthropic(api_key=ANTHROPIC_API_KEY)
                print("[OK] Claude AI conversational CAD generation ready")
            except Exception as e:
                print(f"⚠️ Failed to initialize Claude AI: {str(e)}")
        else:
            if not ANTHROPIC_AVAILABLE:
                print("⚠️ Claude AI library not available")
            elif not ANTHROPIC_API_KEY:
                print("⚠️ ANTHROPIC_API_KEY not found - Claude integration disabled")
        
        print(f"Debug: CloudAIProcessor initialized - Cloud: {cloud_client is not None}, Claude: {self.anthropic_client is not None}")
    
    def process_advanced_command(self, text, context=None):
        """Process command with Claude AI for conversational CAD generation"""
        # Try Claude AI first for conversational CAD generation
        if self.anthropic_client:
            try:
                return self.claude_conversational_process(text, context)
            except Exception as e:
                print(f"Claude conversational processing failed: {str(e)}, falling back")
        
        # Fallback to cloud client
        if self.cloud_client and self.cloud_client.connected:
            return self.cloud_process(text, context)
        else:
            return self.local_process(text, context)
    
    def claude_conversational_process(self, text, context=None):
        """Process using Claude AI for conversational CAD generation"""
        try:
            if not self.anthropic_client:
                print("Claude AI not available for conversational processing")
                return self.local_process(text, context)
            
            # Build comprehensive system prompt for conversational CAD generation
            system_prompt = """You are Axis 5, an expert CAD/manufacturing assistant integrated into FreeCAD. You provide conversational CAD generation and manufacturing intelligence.

Your capabilities:
1. Generate FreeCAD Python code from natural language descriptions
2. Create CAD models (brackets, gears, bottles, holders, containers, etc.)
3. Provide DFM analysis and manufacturing advice
4. Recommend tools, processes, and materials
5. Answer technical questions about CAD and manufacturing
6. Engage in natural conversation about design and manufacturing

When generating CAD code:
- Use FreeCAD Python API (FreeCAD, Part, Draft modules)
- Create objects in the active document
- Include proper recompute() calls
- Make objects visible with appropriate view settings

For manufacturing advice:
- Consider processes like 3D printing, CNC, injection molding
- Provide cost estimates and material recommendations
- Suggest design optimizations for manufacturability

Always be conversational, helpful, and provide practical solutions."""
            
            # Add context if available
            user_message = text
            if context:
                user_message = f"Context: {context}\n\nUser: {text}"
            
            # Add conversation memory for continuity
            if self.context_memory:
                recent_context = "\n".join(self.context_memory[-4:])  # Last 4 exchanges
                user_message = f"Recent conversation:\n{recent_context}\n\nCurrent: {text}"
            
            print(f"🤖 Axis 5 processing: {text[:100]}...")
            
            # Call Claude API for conversational response
            response = self.anthropic_client.messages.create(
                model="claude-3-sonnet-20240229",
                max_tokens=4000,
                system=system_prompt,
                messages=[
                    {"role": "user", "content": user_message}
                ]
            )
            
            response_text = response.content[0].text
            print(f"[OK] Axis 5 response generated: {len(response_text)} chars")
            
            # Store conversation in memory
            self.context_memory.append(f"User: {text}")
            self.context_memory.append(f"Axis 5: {response_text[:200]}...")
            
            # Keep memory manageable
            if len(self.context_memory) > 12:
                self.context_memory = self.context_memory[-12:]
            
            # Extract FreeCAD code if present
            freecad_code = self.extract_freecad_code(response_text)
            
            return {
                'success': True,
                'response': response_text,
                'freecad_code': freecad_code,
                'source': 'claude_conversational',
                'conversation_mode': True
            }
            
        except Exception as e:
            print(f"Error in Claude conversational processing: {str(e)}")
            return {
                'success': False,
                'error': str(e),
                'response': f"Axis 5 AI temporarily unavailable: {str(e)}. Using fallback processing."
            }
    
    def extract_freecad_code(self, text):
        """Extract FreeCAD Python code from Claude's conversational response"""
        try:
            import re
            
            # Look for Python code blocks
            python_pattern = r'```python\s*\n(.*?)\n```'
            matches = re.findall(python_pattern, text, re.DOTALL)
            
            if matches:
                return matches[0].strip()
            
            # Look for general code blocks
            code_pattern = r'```\s*\n(.*?)\n```'
            matches = re.findall(code_pattern, text, re.DOTALL)
            
            if matches:
                # Check if it looks like FreeCAD code
                code = matches[0].strip()
                if any(keyword in code for keyword in ['FreeCAD', 'Part.', 'Draft.', 'doc.addObject', 'App.ActiveDocument']):
                    return code
            
            return None
            
        except Exception as e:
            print(f"Error extracting FreeCAD code: {str(e)}")
            return None
    
    def cloud_process(self, text, context):
        """Use cloud AI for processing"""
        try:
            if not self.cloud_client:
                print("Debug: No cloud client available, falling back to local processing")
                return self.local_process(text, context)
            
            # Build prompt with context
            prompt = self.build_ai_prompt(text, context)
            
            # Query cloud AI
            print(f"Debug: Using cloud client to process: {text}")
            response = self.cloud_client.get_chat_response(prompt)
            
            # Extract response text
            if "response" in response:
                response_text = response["response"]
                try:
                    # Try to parse as JSON
                    if '{' in response_text and '}' in response_text:
                        json_str = response_text[response_text.find('{'):response_text.rfind('}')+1]
                        parsed = json.loads(json_str)
                        return parsed
                    else:
                        return self.parse_text_response(response_text)
                except json.JSONDecodeError:
                    return self.parse_text_response(response_text)
            else:
                return self.local_process(text, context)
        except Exception as e:
            print(f"Cloud AI error: {e}")
            return self.local_process(text, context)
    
    def build_ai_prompt(self, text, context):
        """Build comprehensive prompt for AI"""
        ctx = context or {}
        prompt = f"""I need to create a CAD model based on this description: \"{text}\". 
        Please analyze this request and provide a structured response with the following information:
        
        1. What type of object should be created (e.g., bracket, gear, housing)
        2. The key dimensions and parameters needed
        3. Any specific features that should be added (e.g., holes, fillets)
        4. Any manufacturing constraints to consider
        
        Format your response as a JSON object with these keys: intent, object_type, parameters, features, constraints.
        For example: {{"intent": "create", "object_type": "bracket", "parameters": {{"length": 100, "width": 50, "height": 20}}, "features": ["mounting_holes", "fillets"], "constraints": ["3d_printable"]}}
        """
        
        return prompt
    
    def local_process(self, text, context):
        """Local processing with pattern matching"""
        text_lower = text.lower()
        print(f"Debug: Using local processing for: {text}")
        
        # Basic pattern matching
        result = {
            'intent': 'create',
            'object_type': self.extract_object_type(text),
            'parameters': self.extract_parameters(text),
            'features': [],
            'constraints': []
        }
        
        # Extract features
        if 'hole' in text_lower or 'drill' in text_lower:
            result['features'].append('holes')
        if 'fillet' in text_lower or 'round' in text_lower:
            result['features'].append('fillets')
        if 'chamfer' in text_lower or 'bevel' in text_lower:
            result['features'].append('chamfers')
        
        return result
    
    def extract_object_type(self, text):
        """Extract what type of object to create"""
        objects = ['bracket', 'gear', 'housing', 'enclosure', 'mount', 
                  'plate', 'shaft', 'spacer', 'frame', 'support', 'box', 'cylinder']
        
        text_lower = text.lower()
        for obj in objects:
            if obj in text_lower:
                return obj
        return 'box'  # Default to box
    
    def extract_parameters(self, text):
        """Extract dimensional parameters"""
        params = {}
        
        # Extract dimensions (100x50x20 format)
        dim_match = re.search(r'(\d+)\s*x\s*(\d+)(?:\s*x\s*(\d+))?', text)
        if dim_match:
            params['length'] = float(dim_match.group(1))
            params['width'] = float(dim_match.group(2))
            if dim_match.group(3):
                params['height'] = float(dim_match.group(3))
        else:
            # Default dimensions
            params['length'] = 100.0
            params['width'] = 50.0
            params['height'] = 20.0
        
        return params
    
    def parse_text_response(self, response):
        """Parse text response when JSON parsing fails"""
        result = {
            'intent': 'create',
            'object_type': 'box',
            'parameters': {'length': 100.0, 'width': 50.0, 'height': 20.0},
            'features': [],
            'constraints': []
        }
        
        # Try to extract key information from text
        object_match = re.search(r'object_?type:?\s*(\w+)', response, re.IGNORECASE)
        if object_match:
            result['object_type'] = object_match.group(1).lower()
        
        # Look for dimensions
        length_match = re.search(r'length:?\s*(\d+(?:\.\d+)?)', response, re.IGNORECASE)
        if length_match:
            result['parameters']['length'] = float(length_match.group(1))
            
        width_match = re.search(r'width:?\s*(\d+(?:\.\d+)?)', response, re.IGNORECASE)
        if width_match:
            result['parameters']['width'] = float(width_match.group(1))
            
        height_match = re.search(r'height:?\s*(\d+(?:\.\d+)?)', response, re.IGNORECASE)
        if height_match:
            result['parameters']['height'] = float(height_match.group(1))
            
        return result

# Natural Language CAD Editor
class NaturalLanguageCADEditor:
    """Natural Language CAD Editor with Claude and Text-to-CAD Integration"""
    
    def __init__(self, cloud_client=None):
        """Initialize the NL CAD editor"""
        self.cloud_client = cloud_client
        self.ai_processor = CloudAIProcessor(cloud_client)
        self.context = DesignContextManager()
        
        # Initialize Text-to-CAD integration
        this_dir = os.path.dirname(os.path.abspath(__file__))
        config_path = os.path.join(this_dir, "cloud_config.json")
        try:
            if _TEXT_TO_CAD_AVAILABLE:
                self.text_to_cad = TextToCADIntegration(config_path)
                print(f"Text-to-CAD integration initialized, connected: {self.text_to_cad.connected}")
            else:
                self.text_to_cad = None
                print("Text-to-CAD integration not available")
        except Exception as e:
            print(f"Error initializing Text-to-CAD integration: {str(e)}")
            self.text_to_cad = None
        
        # Initialize Claude/Anthropic integration
        self.anthropic_client = None
        self.claude_available = False
        if _ANTHROPIC_AVAILABLE:
            api_key = load_anthropic_api_key()
            if api_key:
                try:
                    self.anthropic_client = anthropic.Anthropic(api_key=api_key)
                    self.claude_available = True
                    print("Claude/Anthropic integration initialized")
                except Exception as e:
                    print(f"Error initializing Claude: {str(e)}")
            else:
                print("ANTHROPIC_API_KEY not found - Claude features disabled")
        

        self.command_handlers = {}
        
        # Register command handlers
        self.register_command_handler('create', self.handle_create)
        self.register_command_handler('make', self.handle_create)
        self.register_command_handler('add', self.handle_create)
        self.register_command_handler('generate', self.handle_create)
        
        # Register advanced CAD handlers
        self.register_command_handler('gear', self.handle_gear)
        self.register_command_handler('extrude', self.handle_extrude)
        self.register_command_handler('fillet', self.handle_fillet)
        self.register_command_handler('cylinder', self.handle_cylinder)
    
    def register_command_handler(self, keyword, handler):
        """Register a command handler for a keyword"""
        self.command_handlers[keyword.lower()] = handler
    
    def process_command(self, text):
        """Process a natural language CAD command with Claude and Text-to-CAD integration"""
        print(f"Processing CAD command: {text}")
        
        # Check if this is a Text-to-CAD request first
        if self.text_to_cad and self.text_to_cad.is_text_to_cad_request(text):
            return self.handle_text_to_cad_request(text)
        
        # Check if Claude should handle this request
        if self.claude_available and self.should_use_claude(text):
            return self.handle_claude_request(text)
        
        # Check if this is a complex command that needs AI processing
        if self.is_complex_command(text):
            # Use AI processor
            ai_spec = self.ai_processor.process_advanced_command(text, self.context.get_context())
            return self.create_from_ai_spec(ai_spec)
        
        # Simple command processing
        text_lower = text.lower()
        
        # Check for specific advanced commands first
        if 'extrude' in text_lower or 'extend' in text_lower or 'pull' in text_lower:
            print(f"Debug: Detected extrude command: {text}")
            return self.handle_extrude(text)
            
        if 'fillet' in text_lower or 'round' in text_lower or 'corner' in text_lower:
            print(f"Debug: Detected fillet command: {text}")
            return self.handle_fillet(text)
            
        if 'gear' in text_lower or 'cog' in text_lower:
            print(f"Debug: Detected gear command: {text}")
            return self.handle_gear(text)
            
        # Find matching handler for other commands
        for keyword, handler in self.command_handlers.items():
            if keyword in text_lower:
                print(f"Debug: Found handler for keyword: {keyword}")
                return handler(text)
        
        # Default to create handler if no match
        return self.handle_create(text)
    
    def handle_create(self, text):
        """Handle create commands"""
        try:
            # Extract parameters using AI processor
            params = self.ai_processor.local_process(text, self.context.get_context())
            
            # Get object type
            obj_type = params['object_type']
            dimensions = params['parameters']
            
            # Check for specific object types that need special handling
            if obj_type in ['gear']:
                return self.handle_gear(text)
                
            # Create the basic shape
            obj = None
            doc = FreeCAD.ActiveDocument or FreeCAD.newDocument("CADPart")
            
            if obj_type in ['box', 'cube', 'block']:
                length = dimensions.get('length', 100)
                width = dimensions.get('width', 50)
                height = dimensions.get('height', 20)
                
                box = Part.makeBox(length, width, height)
                obj = doc.addObject("Part::Feature", "Box")
                obj.Shape = box
            
            elif obj_type in ['cylinder', 'tube', 'rod', 'shaft']:
                radius = dimensions.get('radius', 10)
                if 'diameter' in dimensions:
                    radius = dimensions['diameter'] / 2
                height = dimensions.get('height', 50)
                
                cylinder = Part.makeCylinder(radius, height)
                obj = doc.addObject("Part::Feature", "Cylinder")
                obj.Shape = cylinder
            
            elif obj_type in ['sphere', 'ball']:
                radius = dimensions.get('radius', 25)
                if 'diameter' in dimensions:
                    radius = dimensions['diameter'] / 2
                
                sphere = Part.makeSphere(radius)
                obj = doc.addObject("Part::Feature", "Sphere")
                obj.Shape = sphere
            
            else:  # Default to box
                length = dimensions.get('length', 100)
                width = dimensions.get('width', 50)
                height = dimensions.get('height', 20)
                
                box = Part.makeBox(length, width, height)
                obj = doc.addObject("Part::Feature", obj_type.capitalize())
                obj.Shape = box
            
            # Commit changes
            doc.recompute()
            
            # Add features if specified
            if 'features' in params:
                for feature in params['features']:
                    if feature == 'holes':
                        # Add holes - simplified implementation
                        pass
                    elif feature == 'fillets':
                        self.add_fillets_to_object(obj, 2.0)  # Default 2mm radius
            
            return {'success': True, 'message': f"Created {obj_type}", 'object': obj}
            
        except Exception as e:
            print(f"Error creating object: {str(e)}")
            traceback.print_exc()
            return {'success': False, 'message': f"Error: {str(e)}"}
    
    def is_complex_command(self, text):
        """Determine if command needs AI processing"""
        complex_indicators = [
            'with', 'that has', 'including', 'having',
            'assembly', 'mechanism', 'system',
            'compatible', 'optimized', 'analyze'
        ]
        
        text_lower = text.lower()
        return any(indicator in text_lower for indicator in complex_indicators)
    
    def create_from_ai_spec(self, ai_spec):
        """Create part from AI specification"""
        try:
            # Check if we have a valid spec
            if not ai_spec or not isinstance(ai_spec, dict):
                return {'success': False, 'message': "Invalid AI specification"}
                
            # Get object type
            obj_type = ai_spec.get('object_type', 'box')
            params = ai_spec.get('parameters', {})
            
            # Create the object
            result = None
            
            if obj_type == 'box':
                length = params.get('length', 100)
                width = params.get('width', 50)
                height = params.get('height', 20)
                
                doc = FreeCAD.ActiveDocument or FreeCAD.newDocument("CADPart")
                box = Part.makeBox(length, width, height)
                obj = doc.addObject("Part::Feature", "Box")
                obj.Shape = box
                doc.recompute()
                
                result = {'success': True, 'message': f"Created box with AI specifications", 'object': obj}
            
            elif obj_type == 'gear':
                teeth = params.get('teeth', 20)
                module = params.get('module', 2.0)
                width = params.get('width', 10.0)
                
                result = self.create_gear(teeth, module, width)
                
            elif obj_type == 'cylinder':
                radius = params.get('radius', 10.0)
                if 'diameter' in params:
                    radius = params['diameter'] / 2
                height = params.get('height', 50.0)
                
                doc = FreeCAD.ActiveDocument or FreeCAD.newDocument("CADPart")
                cylinder = Part.makeCylinder(radius, height)
                obj = doc.addObject("Part::Feature", "Cylinder")
                obj.Shape = cylinder
                doc.recompute()
                
                result = {'success': True, 'message': f"Created cylinder with AI specifications", 'object': obj}
                
            # Add more object types here
                
            if not result:
                return {'success': False, 'message': f"Unsupported object type: {obj_type}"}
                
            return result
            
        except Exception as e:
            print(f"Error creating from AI spec: {str(e)}")
            traceback.print_exc()
            return {'success': False, 'message': f"Error: {str(e)}"}
            
    def handle_gear(self, text):
        """Create a gear based on text description"""
        try:
            print(f"Creating gear from: {text}")
            
            # Extract teeth count
            teeth_match = re.search(r'(\d+)\s*(?:tooth|teeth|toothed)', text, re.IGNORECASE)
            teeth = int(teeth_match.group(1)) if teeth_match else 20
            
            # Extract module if specified
            module_match = re.search(r'module\s*(\d+(?:\.\d+)?)', text, re.IGNORECASE)
            module = float(module_match.group(1)) if module_match else 2.0
            
            # Extract width if specified
            width_match = re.search(r'width\s*(\d+(?:\.\d+)?)', text, re.IGNORECASE)
            width = float(width_match.group(1)) if width_match else 10.0
            
            return self.create_gear(teeth, module, width)
            
        except Exception as e:
            print(f"Error creating gear: {str(e)}")
            traceback.print_exc()
            return {'success': False, 'message': f"Error creating gear: {str(e)}"}
    
    def create_gear(self, teeth=20, module=2.0, width=10.0):
        """Create a gear with the specified parameters"""
        try:
            # Ensure we have an active document
            doc = FreeCAD.ActiveDocument
            if not doc:
                doc = FreeCAD.newDocument("Gear")
            
            # Calculate gear dimensions
            pitch_diameter = teeth * module
            outer_diameter = pitch_diameter + 2 * module  # Addendum
            root_diameter = pitch_diameter - 2.5 * module  # Dedendum
            
            # Create the base cylinder at the root diameter
            base_cylinder = Part.makeCylinder(root_diameter/2, width)
            
            # Create the teeth by adding blocks around the perimeter
            tooth_angle = 360.0 / teeth  # Angle between teeth
            tooth_width_angle = tooth_angle * 0.4  # Width of each tooth in degrees
            
            # Create a compound shape to hold all teeth
            all_teeth = []
            
            for i in range(teeth):
                # Calculate the angle for this tooth
                angle = i * tooth_angle
                
                # Create a tooth as a box
                tooth_height = (outer_diameter - root_diameter) / 2  # Radial height of tooth
                tooth_width = root_diameter * math.sin(math.radians(tooth_width_angle))  # Arc width at root diameter
                
                # Create the tooth as a box
                tooth = Part.makeBox(tooth_height, tooth_width, width)
                
                # Position the tooth at the edge of the root cylinder
                tooth.translate(FreeCAD.Vector(root_diameter/2, -tooth_width/2, 0))
                
                # Rotate the tooth to its position
                tooth.rotate(FreeCAD.Vector(0, 0, 0), FreeCAD.Vector(0, 0, 1), angle)
                
                # Add to our collection
                all_teeth.append(tooth)
            
            # Fuse all teeth with the base cylinder
            gear_shape = base_cylinder
            for tooth in all_teeth:
                gear_shape = gear_shape.fuse(tooth)
            
            # Create a center bore
            bore = module * 5  # Reasonable bore size based on module
            center_hole = Part.makeCylinder(bore/2, width)
            gear_shape = gear_shape.cut(center_hole)
            
            # Create the final object
            gear_obj = doc.addObject("Part::Feature", f"Gear_T{teeth}_M{module}")
            gear_obj.Shape = gear_shape
            
            doc.recompute()
            
            return {
                'success': True,
                'message': f'Created gear: {teeth} teeth, module {module}, \u00f8{pitch_diameter:.1f}mm pitch diameter',
                'object': gear_obj,
                'specs': {
                    'teeth': teeth,
                    'module': module,
                    'pitch_diameter': pitch_diameter,
                    'outer_diameter': outer_diameter,
                    'root_diameter': root_diameter,
                    'width': width
                }
            }
            
        except Exception as e:
            print(f"Error creating gear: {str(e)}")
            traceback.print_exc()
            return {'success': False, 'message': f"Error creating gear: {str(e)}"}
    
    def handle_cylinder(self, text):
        """Create a cylinder based on text description"""
        try:
            # Extract diameter/radius
            diameter_match = re.search(r'diameter\s*(\d+(?:\.\d+)?)', text, re.IGNORECASE)
            radius_match = re.search(r'radius\s*(\d+(?:\.\d+)?)', text, re.IGNORECASE)
            
            radius = 10.0  # Default
            if diameter_match:
                radius = float(diameter_match.group(1)) / 2
            elif radius_match:
                radius = float(radius_match.group(1))
            
            # Extract height/length
            height_match = re.search(r'(?:height|length)\s*(\d+(?:\.\d+)?)', text, re.IGNORECASE)
            height = float(height_match.group(1)) if height_match else 50.0
            
            # Create cylinder
            doc = FreeCAD.ActiveDocument or FreeCAD.newDocument("CADPart")
            cylinder = Part.makeCylinder(radius, height)
            obj = doc.addObject("Part::Feature", "Cylinder")
            obj.Shape = cylinder
            doc.recompute()
            
            return {'success': True, 'message': f"Created cylinder with radius {radius}mm and height {height}mm", 'object': obj}
            
        except Exception as e:
            print(f"Error creating cylinder: {str(e)}")
            traceback.print_exc()
            return {'success': False, 'message': f"Error creating cylinder: {str(e)}"}
    
    def handle_extrude(self, text):
        """Handle extrusion commands with improved reliability"""
        try:
            print(f"Handling extrusion: {text}")
            print("Debug: ===== EXTRUDE OPERATION START =====")
            
            # Extract distance with better pattern matching
            distance_patterns = [
                r'(?:by|to|of)\s*(\d+(?:\.\d+)?)\s*(?:mm|millimeters?)?',
                r'(\d+(?:\.\d+)?)\s*(?:mm|millimeters?)',
                r'extrude.*?(\d+(?:\.\d+)?)',
            ]
            
            distance = 10.0  # Default
            for pattern in distance_patterns:
                distance_match = re.search(pattern, text, re.IGNORECASE)
                if distance_match:
                    distance = float(distance_match.group(1))
                    break
            
            print(f"Debug: Extrusion distance = {distance}mm")
            
            # Extract direction
            direction = 'up'  # Default direction
            if any(word in text.lower() for word in ['down', 'negative', 'inward', 'into']):
                direction = 'down'
            print(f"Debug: Extrusion direction = {direction}")
            
            # Ensure we have an active document
            if not FreeCAD.ActiveDocument:
                print("Debug: No active document, creating one")
                FreeCAD.newDocument("CADPart")
            
            doc = FreeCAD.ActiveDocument
            print(f"Debug: Active document is {doc.Name}")
            
            # Get selection
            try:
                selection = FreeCADGui.Selection.getSelectionEx()
                print(f"Debug: Found {len(selection)} selected objects")
                
                if not selection:
                    print("Debug: No selection found")
                    return {'success': False, 'message': 'Please select a face, sketch, or object to extrude first'}
                
            except Exception as sel_err:
                print(f"Debug: Selection error: {str(sel_err)}")
                return {'success': False, 'message': f'Selection error: {str(sel_err)}'}
            
            # Create extrusion vector
            if direction == 'down':
                extrude_vector = FreeCAD.Vector(0, 0, -distance)
            else:
                extrude_vector = FreeCAD.Vector(0, 0, distance)
            
            print(f"Debug: Extrusion vector: {extrude_vector}")
            
            # Process the selection
            success_count = 0
            error_messages = []
            
            for sel_item in selection:
                try:
                    obj = sel_item.Object
                    print(f"Debug: Processing object: {obj.Name} (Type: {obj.TypeId})")
                    
                    result_obj = None
                    
                    # Case 1: Face selection (most common for extrude commands)
                    if hasattr(sel_item, 'SubObjects') and sel_item.SubObjects:
                        print(f"Debug: Found {len(sel_item.SubObjects)} sub-objects")
                        
                        # Look for faces in the selection using proper FreeCAD API
                        faces = []
                        if hasattr(sel_item, 'SubElementNames'):
                            for sub_name in sel_item.SubElementNames:
                                if sub_name.startswith('Face'):
                                    # Get face index and extract the actual face from the shape
                                    face_index = int(sub_name[4:]) - 1
                                    if face_index < len(obj.Shape.Faces):
                                        faces.append(obj.Shape.Faces[face_index])
                        
                        if faces:
                            print(f"Debug: Found {len(faces)} face(s) to extrude")
                            face = faces[0]  # Use the first face
                            
                            try:
                                print("Debug: Attempting direct face extrusion")
                                extruded_shape = face.extrude(extrude_vector)
                                
                                # Create new object
                                extrude_name = f"Extrude_{obj.Name}_{int(abs(distance))}mm"
                                result_obj = doc.addObject("Part::Feature", extrude_name)
                                result_obj.Shape = extruded_shape
                                result_obj.ViewObject.Visibility = True
                                
                                print(f"Debug: Successfully created face extrusion: {extrude_name}")
                                success_count += 1
                                
                            except Exception as face_err:
                                print(f"Debug: Direct face extrusion failed: {str(face_err)}")
                                error_messages.append(f"Face extrusion failed: {str(face_err)}")
                    
                    # Case 2: Sketch object
                    elif obj.TypeId == "Sketcher::SketchObject":
                        print("Debug: Processing sketch object")
                        try:
                            # Try to create a face from the sketch and extrude it
                            sketch_wires = obj.Shape.Wires
                            if sketch_wires:
                                wire = sketch_wires[0]
                                if wire.isClosed():
                                    face = Part.Face(wire)
                                    extruded_shape = face.extrude(extrude_vector)
                                    
                                    extrude_name = f"Extrude_{obj.Name}_{int(abs(distance))}mm"
                                    result_obj = doc.addObject("Part::Feature", extrude_name)
                                    result_obj.Shape = extruded_shape
                                    result_obj.ViewObject.Visibility = True
                                    
                                    print(f"Debug: Successfully created sketch extrusion: {extrude_name}")
                                    success_count += 1
                                else:
                                    error_messages.append(f"Sketch {obj.Name} is not closed")
                            else:
                                error_messages.append(f"Sketch {obj.Name} has no wires")
                                
                        except Exception as sketch_err:
                            print(f"Debug: Sketch processing failed: {str(sketch_err)}")
                            error_messages.append(f"Sketch processing failed: {str(sketch_err)}")
                    
                    # Case 3: Objects with faces (try to extrude the largest face)
                    elif hasattr(obj, 'Shape') and obj.Shape.Faces:
                        print("Debug: Processing object with faces")
                        try:
                            # Get the largest face (most likely the one to extrude)
                            largest_face = max(obj.Shape.Faces, key=lambda f: f.Area)
                            print("Debug: Attempting clean face extrusion")
                            try:
                                # Create a clean copy of the face to avoid corruption
                                face_copy = largest_face.copy()
                                
                                # Create extrusion using proper FreeCAD extrude method
                                extruded_shape = face_copy.extrude(extrude_vector)
                                
                                # Ensure the shape is valid
                                if not extruded_shape.isValid():
                                    print("Debug: Invalid extruded shape, attempting to fix")
                                    extruded_shape = extruded_shape.fix()
                                
                                extrude_name = f"Extrude_{obj.Name}_{int(abs(distance))}mm"
                                result_obj = doc.addObject("Part::Feature", extrude_name)
                                result_obj.Shape = extruded_shape
                                
                                # Ensure object is visible and properly rendered
                                result_obj.ViewObject.Visibility = True
                                result_obj.ViewObject.DisplayMode = "Flat Lines"  # Clean display mode
                                
                                # Make the extruded object more visible
                                try:
                                    result_obj.ViewObject.ShapeColor = (0.0, 0.8, 0.0)  # Green color
                                    result_obj.ViewObject.Transparency = 20  # Slightly transparent
                                    
                                    # Force document recompute
                                    doc.recompute()
                                    
                                    # Clear selection and select the new object
                                    FreeCADGui.Selection.clearSelection()
                                    FreeCADGui.Selection.addSelection(result_obj)
                                    
                                    # Force view update
                                    FreeCADGui.updateGui()
                                except:
                                    pass
                                
                                print(f"Debug: Successfully created clean face extrusion: {extrude_name}")
                                success_count += 1
                            
                            except Exception as face_err:
                                print(f"Debug: Face extrusion failed: {str(face_err)}")
                                error_messages.append(f"Face extrusion failed: {str(face_err)}")
                            
                        except Exception as obj_err:
                            print(f"Debug: Object face extrusion failed: {str(obj_err)}")
                            error_messages.append(f"Object extrusion failed: {str(obj_err)}")
                    
                    else:
                        error_messages.append(f"Object {obj.Name} cannot be extruded (type: {obj.TypeId})")
                    
                except Exception as item_err:
                    print(f"Debug: Error processing selection item: {str(item_err)}")
                    error_messages.append(f"Processing error: {str(item_err)}")
            
            # Recompute document
            doc.recompute()
            
            # Update view
            if FreeCADGui.ActiveDocument:
                try:
                    FreeCADGui.ActiveDocument.ActiveView.viewAxometric()
                    FreeCADGui.updateGui()
                except:
                    pass  # View update is not critical
            
            # Return results
            if success_count > 0:
                message = f"Successfully extruded {success_count} item(s) by {distance}mm {direction}"
                if error_messages:
                    message += f" (with {len(error_messages)} errors)"
                
                print(f"Debug: {message}")
                print("Debug: ===== EXTRUDE OPERATION COMPLETE =====")
                return {'success': True, 'message': message}
            else:
                error_summary = "; ".join(error_messages) if error_messages else "Unknown error"
                print(f"Debug: No extrusions created. Errors: {error_summary}")
                print("Debug: ===== EXTRUDE OPERATION FAILED =====")
                return {'success': False, 'message': f'No extrusions created. {error_summary}'}
                
        except Exception as e:
            print(f"Error during extrusion: {str(e)}")
            traceback.print_exc()
            print("Debug: ===== EXTRUDE OPERATION FAILED =====")
            return {'success': False, 'message': f"Error during extrusion: {str(e)}"}
    
    def handle_fillet(self, text):
        """Handle fillet commands"""
        try:
            print(f"Handling fillet: {text}")
            
            # Extract radius
            radius_match = re.search(r'(?:radius|of)\s*(\d+(?:\.\d+)?)\s*(?:mm)?', text, re.IGNORECASE)
            radius = float(radius_match.group(1)) if radius_match else 2.0
            print(f"Debug: Fillet radius = {radius}mm")
            
            # Check if edges are selected
            try:
                selection = FreeCADGui.Selection.getSelectionEx()
                print(f"Debug: Found {len(selection)} selected objects")
                
                if not selection:
                    # If no selection, try to select the most recently created object
                    doc = FreeCAD.ActiveDocument
                    if doc and len(doc.Objects) > 0:
                        # Get the last created object
                        last_obj = doc.Objects[-1]
                        print(f"Debug: Auto-selecting last created object: {last_obj.Name}")
                        FreeCADGui.Selection.addSelection(last_obj)
                        selection = FreeCADGui.Selection.getSelectionEx()
                    else:
                        print("Debug: No objects in document to select")
                        return {'success': False, 'message': 'Please select an object or edges first'}
            except Exception as sel_err:
                print(f"Debug: Error during selection: {str(sel_err)}")
                traceback.print_exc()
                return {'success': False, 'message': f"Selection error: {str(sel_err)}"}
            
            results = []
            for sel_obj in selection:
                obj = sel_obj.Object
                print(f"Debug: Processing object for fillet: {obj.Name}")
                
                if not hasattr(obj, 'Shape') or not hasattr(obj.Shape, 'Edges') or len(obj.Shape.Edges) == 0:
                    print(f"Debug: Object {obj.Name} has no edges to fillet")
                    continue
                    
                print(f"Debug: Object has {len(obj.Shape.Edges)} edges")
                
                # Check if specific edges are selected
                selected_edges = []
                if hasattr(sel_obj, 'SubElementNames') and sel_obj.SubElementNames:
                    print(f"Debug: Found {len(sel_obj.SubElementNames)} sub-elements")
                    for sub in sel_obj.SubElementNames:
                        if sub.startswith('Edge'):
                            edge_idx = int(sub.replace('Edge', '')) - 1
                            selected_edges.append(edge_idx)
                            print(f"Debug: Selected edge {edge_idx}")
                
                # If no specific edges selected, use all edges
                if not selected_edges:
                    print("Debug: No specific edges selected, using all edges")
                    selected_edges = list(range(len(obj.Shape.Edges)))
                
                if not selected_edges:
                    print(f"Debug: No edges found for object {obj.Name}")
                    continue
                
                try:
                    # Create fillet
                    fillet_name = f"Fillet_{obj.Name}"
                    print(f"Debug: Creating fillet object {fillet_name}")
                    fillet = FreeCAD.ActiveDocument.addObject("Part::Fillet", fillet_name)
                    fillet.Base = obj
                    
                    # Add edges to fillet
                    edge_strings = []
                    for edge_idx in selected_edges:
                        if edge_idx < len(obj.Shape.Edges):
                            edge_strings.append((edge_idx+1, radius, radius))
                    
                    print(f"Debug: Adding {len(edge_strings)} edges to fillet")
                    fillet.Edges = edge_strings
                    
                    # Hide original object
                    if hasattr(FreeCADGui, "ActiveDocument") and FreeCADGui.ActiveDocument:
                        try:
                            FreeCADGui.ActiveDocument.getObject(obj.Name).Visibility = False
                            print(f"Debug: Set original object {obj.Name} visibility to False")
                        except Exception as vis_err:
                            print(f"Debug: Error setting visibility: {str(vis_err)}")
                    
                    results.append({
                        'object': fillet,
                        'radius': radius,
                        'edges': len(edge_strings)
                    })
                    print(f"Debug: Successfully added fillet to results")
                except Exception as fillet_err:
                    print(f"Debug: Error creating fillet: {str(fillet_err)}")
                    traceback.print_exc()
            
            # Recompute document
            FreeCAD.ActiveDocument.recompute()
            
            if not results:
                return {'success': False, 'message': 'No fillets were created'}
                
            return {
                'success': True,
                'message': f'Created {len(results)} fillet(s) with radius {radius}mm',
                'fillets': results
            }
            
        except Exception as e:
            print(f"Error creating fillet: {str(e)}")
            traceback.print_exc()
            return {'success': False, 'message': f"Error creating fillet: {str(e)}"}
    
    def should_use_claude(self, text):
        """Determine if Claude should handle this request"""
        if not self.claude_available:
            return False
        
        # Use Claude for conversational requests, complex analysis, or when explicitly asked
        claude_keywords = [
            'explain', 'how', 'why', 'what', 'analyze', 'recommend', 'suggest',
            'compare', 'optimize', 'improve', 'claude', 'ai', 'help me understand'
        ]
        
        text_lower = text.lower()
        return any(keyword in text_lower for keyword in claude_keywords)
    
    def handle_claude_request(self, text):
        """Handle request using Claude AI"""
        try:
            # Get current CAD context
            context = self.context.get_context()
            
            # Build comprehensive prompt for Claude
            system_prompt = """You are an expert manufacturing engineer and CAD specialist integrated into FreeCAD. 
You help users with:
- CAD design and modeling
- Manufacturing processes and DFM analysis
- Material selection and optimization
- Engineering calculations and recommendations

Provide practical, actionable advice. If the user wants to create CAD geometry, provide specific FreeCAD Python code."""
            
            user_prompt = f"""Current CAD Context:
{context}

User Request: {text}

Please provide a helpful response with specific recommendations or FreeCAD code if applicable."""
            
            # Call Claude API
            response = self.anthropic_client.messages.create(
                model="claude-3-sonnet-20240229",
                max_tokens=2000,
                system=system_prompt,
                messages=[
                    {"role": "user", "content": user_prompt}
                ]
            )
            
            claude_response = response.content[0].text
            
            return {
                'success': True,
                'message': claude_response,
                'source': 'Claude AI',
                'type': 'conversational'
            }
            
        except Exception as e:
            print(f"Error with Claude request: {str(e)}")
            # Fallback to regular processing
            return self.ai_processor.process_advanced_command(text, self.context.get_context())
    
    def handle_text_to_cad_request(self, text):
        """Handle a Text-to-CAD request using the cloud service"""
        if not self.text_to_cad:
            return {
                "success": False,
                "message": "Text-to-CAD integration is not available"
            }
            
        try:
            print(f"Processing Text-to-CAD request: {text}")
            
            # Process the request using TextToCADIntegration
            result = self.text_to_cad.process_request(text)
            
            # Execute the FreeCAD code to actually create the CAD object
            if result.get("success", False):
                freecad_code = result.get("freecad_code", "")
                print(f"Got FreeCAD code with length: {len(freecad_code)}")
                if freecad_code:
                    print(f"About to execute FreeCAD code via execute_freecad_code")
                    
                    execution_result = self.text_to_cad.execute_freecad_code(freecad_code)
                    print(f"Execution result: {execution_result}")
                    
                    if not execution_result.get("success", False):
                        print(f"Failed to execute FreeCAD code: {execution_result.get('error', 'Unknown error')}")
                        return {
                            "success": False,
                            "message": f"Failed to execute CAD code: {execution_result.get('error', 'Unknown error')}"
                        }
                    else:
                        print("FreeCAD code executed successfully - CAD object should be visible in 3D view")
                else:
                    print("No FreeCAD code received from server")
                
                return {
                    "success": True,
                    "message": result.get("message", "CAD model created successfully"),
                    "engineering_analysis": result.get("engineering_analysis", "")
                }
            else:
                error_msg = result.get("error", "Unknown error in Text-to-CAD request")
                print(f"Text-to-CAD request failed: {error_msg}")
                return {
                    "success": False,
                    "message": f"Text-to-CAD failed: {error_msg}"
                }
                
        except Exception as e:
            print(f"Error in Text-to-CAD request: {str(e)}")
            traceback.print_exc()
            return {
                "success": False,
                "message": f"Text-to-CAD error: {str(e)}"
            }
    
    def add_fillets_to_object(self, obj, radius=2.0):
        """Add fillets to all edges of an object"""
        try:
            if not obj or not hasattr(obj, 'Shape') or not hasattr(obj.Shape, 'Edges'):
                return False
                
            # Create fillet
            fillet_name = f"Fillet_{obj.Name}"
            fillet = FreeCAD.ActiveDocument.addObject("Part::Fillet", fillet_name)
            fillet.Base = obj
            
            # Add all edges to fillet
            edge_strings = []
            for i in range(len(obj.Shape.Edges)):
                edge_strings.append((i+1, radius, radius))
            
            fillet.Edges = edge_strings
            
            # Hide original object
            if hasattr(FreeCADGui, "ActiveDocument") and FreeCADGui.ActiveDocument:
                FreeCADGui.ActiveDocument.getObject(obj.Name).Visibility = False
            
            # Recompute document
            FreeCAD.ActiveDocument.recompute()
            
            return True
            
        except Exception as e:
            print(f"Error adding fillets: {str(e)}")
            return False

    def handle_text_to_cad_request(self, text):
        """Handle a Text-to-CAD request using the cloud service"""
        if not self.text_to_cad:
            return {
                "success": False,
                "message": "Text-to-CAD integration is not available"
            }
            
        try:
            print(f"Processing Text-to-CAD request: {text}")
            
            # Create a progress callback function
            def progress_callback(message):
                print(f"Text-to-CAD progress: {message}")
            
            # Process the request using the improved TextToCADIntegration
            result = self.text_to_cad.process_request(text)
            
            # Execute the FreeCAD code to actually create the CAD object and make it visible - AXIS 5 DEBUG
            if result.get("success", False):
                freecad_code = result.get("freecad_code", "")
                print(f"🔍 AXIS 5 DEBUG: Got FreeCAD code with length: {len(freecad_code)}")
                if freecad_code:
                    print(f"🔍 AXIS 5 DEBUG: About to execute FreeCAD code via enhanced execute_freecad_code")
                    print(f"🔍 AXIS 5 DEBUG: First 200 chars of code: {freecad_code[:200]}...")
                    
                    execution_result = self.text_to_cad.execute_freecad_code(freecad_code)
                    print(f"🔍 AXIS 5 DEBUG: Execution result: {execution_result}")
                    
                    if not execution_result.get("success", False):
                        print(f"❌ AXIS 5 DEBUG: Failed to execute FreeCAD code: {execution_result.get('error', 'Unknown error')}")
                        return {
                            "success": False,
                            "message": f"Failed to execute CAD code: {execution_result.get('error', 'Unknown error')}"
                        }
                    else:
                        print("[OK] AXIS 5 DEBUG: FreeCAD code executed successfully - CAD object should be visible in 3D view")
                        print(f"[OK] AXIS 5 DEBUG: Enhanced GUI updates should have been applied for visibility")
                else:
                    print("❌ AXIS 5 DEBUG: No FreeCAD code received from server")
                
                return {
                    "success": True,
                    "message": result.get("message", "CAD model created successfully"),
                    "engineering_analysis": result.get("engineering_analysis", "")
                }
            else:
                error_msg = result.get("message", "Unknown error in Text-to-CAD request")
                print(f"Text-to-CAD request failed: {error_msg}")
                return {
                    "success": False,
                    "message": f"Failed to process Text-to-CAD request: {error_msg}",
                    "fallback_available": result.get("fallback_available", False)
                }
                
        except Exception as e:
            print(f"Error in Text-to-CAD request: {str(e)}")
            traceback.print_exc()
            return {
                "success": False,
                "message": f"Error processing Text-to-CAD request: {str(e)}"
            }

class CloudApiClient:
    """Client for communicating with the Manufacturing Co-Pilot Cloud API"""
    
    # Default endpoint for CAD analysis
    default_analysis_endpoint = "/api/analysis/cad"
    
    @classmethod
    def load_cloud_config(cls):
        """Load cloud configuration from JSON file if available"""
        try:
            # Check for config file in the same directory as this script
            script_dir = os.path.dirname(os.path.realpath(__file__))
            config_file = os.path.join(script_dir, "cloud_config.json")
            
            if os.path.exists(config_file):
                print(f"Loading cloud configuration from {config_file}")
                with open(config_file, "r") as f:
                    cloud_config = json.load(f)
                
                # Update default endpoint if specified
                if "default_analysis_endpoint" in cloud_config:
                    cls.default_analysis_endpoint = cloud_config["default_analysis_endpoint"]
                    print(f"Using custom analysis endpoint: {cls.default_analysis_endpoint}")
                
                return cloud_config
            else:
                print("No cloud_config.json file found, using defaults")
                return {}
        except Exception as e:
            print(f"Error loading cloud configuration: {e}")
            return {}
    
    def __init__(self, api_url: str = None, api_key: str = None):
        """Initialize the cloud API client"""
        # Load cloud configuration
        cloud_config = self.load_cloud_config()
        
        # Store the entire config in the instance
        self.config = cloud_config
        
        # Set API URL and key from config or parameters
        self.api_url = api_url or cloud_config.get("cloud_api_url", "https://freecad-copilot-service-501520737043.asia-south1.run.app")
        self.api_key = api_key or cloud_config.get("cloud_api_key", "dev_api_key_for_testing")
        self.default_analysis_endpoint = self.default_analysis_endpoint or cloud_config.get("default_analysis_endpoint", "/api/analysis/cad")
        self.timeout = cloud_config.get("connection_timeout", 10)  # Default timeout in seconds
        
        # Print debug info about DFM endpoint
        if "dfm_endpoint" in cloud_config:
            print(f"DEBUG: Loaded DFM endpoint from config: {cloud_config['dfm_endpoint']}")
        else:
            print("DEBUG: No DFM endpoint found in config")
            # Add default DFM endpoint if not present
            # Use the analysis endpoint for DFM since the dedicated DFM endpoint doesn't exist
            self.config["dfm_endpoint"] = "/api/analysis/cad"
        self.last_error = None
        self.connected = False
        self.connection_quality = "unknown"  # unknown, poor, fair, good, excellent
        self.last_latency = 0  # in ms
        self.last_check_time = 0
        self.connection_listeners = []  # callbacks for connection status changes
        
        # Test connection on init
        self.test_connection()
    
    def test_connection(self) -> bool:
        """Test connection to the cloud API"""
        try:
            # Load timeout from config or use default
            cloud_config = self.load_cloud_config()
            timeout = cloud_config.get("connection_timeout", 10)
            retry_count = cloud_config.get("retry_count", 3)
            
            # Only use the known working endpoint to avoid 404 errors
            endpoints_to_try = ["/health"]
            
            print(f"Testing connection with endpoint: {endpoints_to_try[0]}")
            
            # Try each endpoint with retries
            for endpoint in endpoints_to_try:
                for attempt in range(retry_count):
                    try:
                        start_time = time.time()
                        response = self._make_request(endpoint, method="GET", timeout=timeout)
                        end_time = time.time()
                        
                        # Calculate latency in milliseconds
                        latency = int((end_time - start_time) * 1000)
                        self.last_latency = latency
                        self.last_check_time = time.time()
                        
                        # Determine connection quality based on latency
                        if latency < 200:
                            self.connection_quality = "excellent"
                        elif latency < 500:
                            self.connection_quality = "good"
                        elif latency < 1000:
                            self.connection_quality = "fair"
                        else:
                            self.connection_quality = "poor"
                            
                        # Connection successful
                        old_status = self.connected
                        self.connected = True
                        
                        # Notify listeners if status changed
                        if not old_status and self.connected:
                            self._notify_connection_change()
                            
                        return True
                    except Exception as e:
                        print(f"Attempt {attempt+1}/{retry_count} failed for endpoint {endpoint}: {str(e)}")
                        if attempt == retry_count - 1:
                            continue  # Try next endpoint
                        time.sleep(0.5)  # Brief delay between retries
            
            # If we get here, all endpoints failed
            self.last_error = "Failed to connect to cloud API"
            old_status = self.connected
            self.connected = False
            self.connection_quality = "poor"  # Set to poor instead of unknown for UI clarity
            
            # Try one more time with the default API key
            print("Trying connection with default API key...")
            self.api_key = "dev_api_key_for_testing"
            
            # Try the most reliable endpoint with the default key
            try:
                response = self._make_request("/health", method="GET", timeout=timeout)
                print("Connection successful with default API key")
                self.connected = True
                self.connection_quality = "fair"
                
                # Update the config file with the working API key
                if hasattr(self, 'config'):
                    self.config["cloud_api_key"] = self.api_key
                    self._save_config_to_file()
                    
                # Notify listeners of the connection change
                self._notify_connection_change()
                return True
            except Exception as e:
                print(f"Connection with default API key also failed: {str(e)}")
            
            # If we still can't connect, return a local fallback response
            return False
        except Exception as e:
            self.last_error = str(e)
            old_status = self.connected
            self.connected = False
            self.connection_quality = "unknown"
            
            # Notify listeners if status changed
            if old_status and not self.connected:
                self._notify_connection_change()
            
            return False
    
    def get_chat_response(self, message: str) -> Dict[str, Any]:
        """Get a response from the cloud API for a chat message"""
        try:
            # Get active document info if available
            cad_data = self._get_cad_data()
            
            # Check if this is a DFM analysis request
            message_lower = message.lower()
            dfm_terms = [
                "dfm", 
                "check for manufacturability",
                "design for manufacturing",
                "manufacturable",
                "3d print",
                "3d printing",
                "printable",
                "can this be printed",
                "can this be manufactured",
                "cnc",
                "machining",
                "machinable",
                "manufacturing issues",
                "manufacturing problems",
                "manufacturing constraints",
                "check this part"
            ]
            # Log the message for debugging
            print(f"DEBUG: Checking if message is DFM request: '{message}'")
            
            # Check if any DFM term is in the message
            is_dfm_request = any(term in message_lower for term in dfm_terms)
            print(f"DEBUG: Is DFM request: {is_dfm_request}")
            
            # Prepare payload for analysis endpoint
            payload = {
                "message": message,
                "timestamp": time.strftime("%Y-%m-%dT%H:%M:%S"),
                "mode": "general",
                "cad_data": cad_data
            }
            
            # Determine which endpoint to use
            endpoint = self.default_analysis_endpoint
            
            # Debug config information
            print(f"DEBUG: Has config attribute: {hasattr(self, 'config')}")
            if hasattr(self, 'config'):
                print(f"DEBUG: Config keys: {list(self.config.keys())}")
                print(f"DEBUG: DFM endpoint in config: {'dfm_endpoint' in self.config}")
                if 'dfm_endpoint' in self.config:
                    print(f"DEBUG: DFM endpoint value: {self.config['dfm_endpoint']}")
            
            # If this is a DFM request and dfm_endpoint is configured, use it
            if is_dfm_request:
                print("DEBUG: This is a DFM request")
                if hasattr(self, 'config') and 'dfm_endpoint' in self.config:
                    print(f"DEBUG: Using DFM endpoint: {self.config['dfm_endpoint']}")
                    endpoint = self.config['dfm_endpoint']
                else:
                    print("DEBUG: No DFM endpoint configured, using default endpoint")
            else:
                print("DEBUG: Not a DFM request, using default endpoint")
            
            # Prepare the appropriate payload based on the endpoint
            request_payload = payload
            
            # If this is a DFM request, format the payload appropriately
            if is_dfm_request:
                print("DEBUG: Formatting payload for DFM endpoint")
                
                # Format payload for the new DFM endpoint structure
                print("DEBUG: Formatting payload for new DFM endpoint structure")
                
                # Extract CAD data
                if 'cad_data' not in payload:
                    print("ERROR: Missing cad_data in payload")
                    payload['cad_data'] = {}
                
                cad_data = payload['cad_data']
                part_name = cad_data.get('name', 'Unknown Part')
                
                # Default values
                material = cad_data.get('material', 'ABS')
                process = 'fdm'  # Default to FDM 3D printing
                
                # Extract manufacturing intent from message if available
                message = payload.get('message', '').lower()
                
                # More detailed process detection
                if 'cnc' in message or 'machin' in message or 'mill' in message:
                    process = 'cnc'
                    print(f"DEBUG: Detected CNC machining process from query: '{message}'")
                elif '3d print' in message or 'fdm' in message or 'printing' in message or 'printed' in message:
                    process = 'fdm'
                    print(f"DEBUG: Detected 3D printing process from query: '{message}'")
                elif 'injection' in message or 'molding' in message or 'moulding' in message:
                    process = 'injection_molding'
                    print(f"DEBUG: Detected injection molding process from query: '{message}'")
                
                print(f"DEBUG: Selected manufacturing process: {process}")
                
                # Extract features from CAD data
                features = []
                
                # Add walls if we have thickness information
                if 'dimensions' in cad_data and 'thickness' in cad_data['dimensions']:
                    features.append({
                        "type": "wall",
                        "dimensions": {"thickness": cad_data['dimensions'].get('thickness', 1.5)},
                        "geometry_ref": {"face_index": None}
                    })
                
                # Add fillets if we have radius information
                if 'manufacturing_features' in cad_data and 'min_fillet_radius' in cad_data['manufacturing_features']:
                    features.append({
                        "type": "fillet",
                        "dimensions": {"radius": cad_data['manufacturing_features'].get('min_fillet_radius', 0.5)},
                        "geometry_ref": {"edge_index": None}
                    })
                
                # Add holes if we have any in the features
                if 'manufacturing_features' in cad_data and 'holes' in cad_data['manufacturing_features']:
                    hole_count = cad_data['manufacturing_features'].get('holes', 0)
                    if hole_count > 0:
                        features.append({
                            "type": "hole",
                            "dimensions": {"diameter": 2.0},  # Default diameter
                            "geometry_ref": {"face_index": None}
                        })
                
                # Create the DFM-specific payload that works with both endpoints
                dfm_data = {
                    "material": material,
                    "process": process,
                    "features": features,
                    "tolerances": {"general": 0.1},
                    "surface_finish": "normal"
                }
                
                # Integrate DFM data into the standard payload format
                request_payload = {
                    "message": payload["message"],
                    "timestamp": payload["timestamp"],
                    "mode": "dfm",  # Set mode to dfm
                    "cad_data": payload["cad_data"],
                    "dfm_data": dfm_data,  # Add the DFM-specific data
                    "analysis_type": "dfm",
                    "manufacturing_process": process,  # Explicitly specify the manufacturing process
                    "query_intent": {
                        "process_specific": True,
                        "process_type": process,
                        "original_query": payload["message"]
                    }
                }
                
                print(f"DEBUG: New DFM payload: {request_payload}")
                print(f"DEBUG: Enhanced payload for DFM: {request_payload}")
                print(f"DEBUG: DFM payload: {request_payload}")
            
            # Try the selected endpoint with retries
            max_retries = 3
            retry_delay = 1  # seconds
            
            # For DFM requests, use the dedicated endpoint if available
            if is_dfm_request:
                # Check if we should use the new dedicated DFM endpoint
                if self.config.get('use_dedicated_dfm_endpoint', False) and '/check_dfm' in self.config.get('dfm_endpoint', ''):
                    # Use the dedicated endpoint without query parameters
                    print(f"DEBUG: Using dedicated DFM endpoint: {endpoint}")
                else:
                    # Fall back to the analysis endpoint with query parameters
                    endpoint = f"{endpoint}?analysis_type=dfm&process={process}"
                    print(f"DEBUG: Using analysis endpoint with DFM and process parameters: {endpoint}")
            
            for attempt in range(1, max_retries + 1):
                try:
                    if attempt > 1:
                        print(f"Retry attempt {attempt}/{max_retries} for endpoint {endpoint}")
                    response = self._make_request(endpoint, payload=request_payload)
                    # If successful, update connection status
                    if not self.connected:
                        old_status = self.connected
                        self.connected = True
                        if old_status != self.connected:
                            self._notify_connection_change()
                
                    # For DFM requests, format the response appropriately
                    if is_dfm_request:
                        print("DEBUG: Formatting DFM response")
                        print(f"DEBUG: Response keys: {response.keys() if isinstance(response, dict) else 'Not a dict'}")                        
                        # Get part name from payload
                        part_name = "Unknown Part"
                        original_query = ""
                        if isinstance(payload, dict):
                            if 'cad_data' in payload:
                                part_name = payload['cad_data'].get('name', 'Unknown Part')
                            elif 'material' in payload and 'features' in payload:
                                # This is the new DFM payload format
                                part_name = "Part"
                            
                            # Store the original query for context
                            original_query = payload.get('message', '')
                            
                        # Add the original query to the response for context
                        if isinstance(response, dict) and original_query:
                            response['original_query'] = original_query
                        
                        # Create a DFM-specific response
                        if isinstance(response, dict):
                            # Check if this is a response from the new DFM endpoint
                            if 'violations' in response:
                                print("DEBUG: Found violations data in response (new DFM format)")
                                dfm_response = {
                                    "response": self._format_dfm_response(response, part_name),
                                    "timestamp": time.strftime("%Y-%m-%dT%H:%M:%S")
                                }
                                return dfm_response
                            # Check if this is an analysis result with manufacturability data (legacy format)
                            elif 'manufacturability_index' in response or 'design_issues' in response:
                                print("DEBUG: Found manufacturability data in response (legacy format)")
                                
                                # Determine if this is a process-specific query
                                process_type = ''
                                if original_query:
                                    if '3d print' in original_query.lower() or 'printed' in original_query.lower() or 'printing' in original_query.lower():
                                        process_type = 'fdm'
                                        print(f"DEBUG: Detected 3D printing query: '{original_query}'")
                                    elif 'cnc' in original_query.lower() or 'machin' in original_query.lower() or 'mill' in original_query.lower():
                                        process_type = 'cnc'
                                        print(f"DEBUG: Detected CNC machining query: '{original_query}'")
                                
                                # Add process type to the response
                                if process_type:
                                    response['manufacturing_process'] = process_type
                                
                                dfm_response = {
                                    "response": self._format_dfm_response(response, part_name),
                                    "timestamp": time.strftime("%Y-%m-%dT%H:%M:%S")
                                }
                                return dfm_response
                
                    return response
                except Exception as e:
                    print(f"Primary endpoint attempt {attempt} failed: {str(e)}")
                    if attempt < max_retries:
                        print(f"Waiting {retry_delay}s before retry...")
                        time.sleep(retry_delay)
                        retry_delay *= 2  # Exponential backoff
                    else:
                        first_error = e
            
            # If we get here, all primary endpoint attempts failed
            print("All primary endpoint attempts failed, trying fallbacks")
            
            # Try fallback endpoints if available
            if hasattr(self, 'config') and 'fallback_endpoints' in self.config:
                for endpoint in self.config['fallback_endpoints']:
                    try:
                        print(f"Trying fallback endpoint: {endpoint}")
                        response = self._make_request(endpoint, payload=payload)
                        return response
                    except Exception as e:
                        print(f"Fallback endpoint {endpoint} failed: {str(e)}")
            
            # If all endpoints fail, try the /api/chat endpoint as last resort
            try:
                print("Trying generic chat endpoint: /api/chat")
                chat_payload = {"message": message}
                response = self._make_request("/api/chat", payload=chat_payload)
                return response
            except Exception as e:
                print(f"Chat endpoint failed: {str(e)}")
                
                # Force reconnection attempt
                print("Attempting to reconnect to cloud service...")
                self.test_connection()
                
                # If reconnection successful, try one more time with the original endpoint
                if self.connected:
                    print("Reconnected successfully, retrying original request")
                    try:
                        response = self._make_request(endpoint, payload=request_payload)
                        return response
                    except Exception as retry_error:
                        print(f"Retry after reconnection failed: {str(retry_error)}")
                        
                # If we still can't connect, return a local fallback response
                return {
                    "response": "I'm processing your request locally. Cloud connection is currently unavailable.",
                    "timestamp": time.strftime("%Y-%m-%dT%H:%M:%S")
                }
                
            # If we get here, all endpoints failed
            raise Exception(f"All endpoints failed. Primary error: {str(first_error)}")
        except Exception as e:
            self.last_error = str(e)
            # Update connection status if needed
            if self.connected:
                old_status = self.connected
                self.connected = False
                self.connection_quality = "unknown"
                if old_status != self.connected:
                    self._notify_connection_change()
            
            return {
                "error": str(e),
                "response": f"⚠️ Cloud connection error: {str(e)}. Please check your internet connection and API configuration.\n\nYou can click on the connection indicator to retry.",
                "timestamp": time.strftime("%Y-%m-%dT%H:%M:%S")
            }
    
    def _get_cad_data(self) -> Dict[str, Any]:
        """Get CAD data from active document if available"""
        try:
            import FreeCAD
            
            if FreeCAD.ActiveDocument:
                doc = FreeCAD.ActiveDocument
                objects = doc.Objects
                
                # Basic document info
                doc_info = {
                    "name": doc.Name,
                    "object_count": len(objects),
                    "objects": []
                }
                
                # Get info about each object
                for obj in objects:
                    obj_info = {
                        "name": obj.Name,
                        "label": obj.Label,
                        "type": obj.TypeId
                    }
                    
                    # Add shape info if available
                    if hasattr(obj, 'Shape'):
                        bbox = obj.Shape.BoundBox
                        obj_info["dimensions"] = {
                            "x": bbox.XLength,
                            "y": bbox.YLength,
                            "z": bbox.ZLength
                        }
                        obj_info["volume"] = obj.Shape.Volume
                    
                    doc_info["objects"].append(obj_info)
                
                return doc_info
            else:
                return {"status": "no_active_document"}
                
        except Exception as e:
            print(f"Error getting CAD data: {e}")
            return {"status": "error", "message": str(e)}
    
    def _make_request(self, endpoint: str, payload: Dict[str, Any] = None, method: str = "POST", timeout: int = None) -> Dict[str, Any]:
        """Make a request to the cloud API"""
        url = f"{self.api_url}{endpoint}"
        
        # Set up headers with API key if available
        headers = {"Content-Type": "application/json"}
        if self.api_key:
            # Use X-API-Key as the primary authentication method
            # This is the standard expected by the cloud service
            headers["X-API-Key"] = self.api_key
            print("Using X-API-Key authentication")
        
        # Use provided timeout or default from config
        if timeout is None:
            cloud_config = self.load_cloud_config()
            timeout = cloud_config.get("connection_timeout", 10)
        
        try:
            print(f"Making {method} request to {url} with timeout {timeout}s")
            start_time = time.time()
            
            if method == "GET":
                response = requests.get(url, headers=headers, timeout=timeout)
            elif method == "POST":
                response = requests.post(url, json=payload, headers=headers, timeout=timeout)
            else:
                raise ValueError(f"Unsupported HTTP method: {method}")
            
            # Calculate latency
            end_time = time.time()
            latency = int((end_time - start_time) * 1000)
            self.last_latency = latency
            
            # Log response status
            print(f"Response status code: {response.status_code}, latency: {latency}ms")
            
            # Check if response is successful
            if response.status_code >= 400:
                print(f"Error response: {response.text}")
                
                # Handle specific error codes
                if response.status_code == 401:
                    # Authentication error - try to recover
                    print("Authentication error. Trying to recover...")
                    # Reload config to get fresh API key
                    cloud_config = self.load_cloud_config()
                    self.api_key = cloud_config.get("cloud_api_key", "dev_api_key_for_testing")
                    raise ValueError(f"Authentication failed: {response.text}. Updated API key for next attempt.")
                elif response.status_code == 404:
                    # Not found error
                    raise ValueError(f"Endpoint not found: {endpoint}")
                elif response.status_code == 422 and 'cad_data' in response.text:
                    raise ValueError("API requires cad_data field")
            
            response.raise_for_status()
            
            # Update connection quality based on latency
            if latency < 200:
                self.connection_quality = "excellent"
            elif latency < 500:
                self.connection_quality = "good"
            elif latency < 1000:
                self.connection_quality = "fair"
            else:
                self.connection_quality = "poor"
            
            # Parse response
            return response.json()
            
        except requests.exceptions.RequestException as e:
            self.last_error = str(e)
            print(f"Cloud API request failed: {str(e)}")
            if hasattr(e, 'response') and e.response is not None:
                print(f"Response status code: {e.response.status_code}")
                try:
                    print(f"Response content: {e.response.text}")
                except:
                    pass
            # Update connection status
            old_status = self.connected
            self.connected = False
            self.connection_quality = "unknown"
            
            # Notify listeners if status changed
            if old_status and not self.connected:
                self._notify_connection_change()
                
            raise Exception(f"Cloud API request failed: {str(e)}")
        
        except Exception as e:
            self.last_error = str(e)
            print(f"Unexpected error: {str(e)}")
            raise

    def add_connection_listener(self, callback):
        """Add a callback function to be notified of connection status changes"""
        if callback not in self.connection_listeners:
            self.connection_listeners.append(callback)
    
    def remove_connection_listener(self, callback):
        """Remove a connection status callback"""
        if callback in self.connection_listeners:
            self.connection_listeners.remove(callback)
    
    def _notify_connection_change(self):
        """Notify all listeners of connection status change"""
        for callback in self.connection_listeners:
            try:
                callback(self.connected, self.connection_quality, self.last_latency)
            except Exception as e:
                print(f"Error in connection listener callback: {str(e)}")
                
    def _save_config_to_file(self):
        """Save the current configuration to the config file"""
        try:
            if hasattr(self, 'config'):
                script_dir = os.path.dirname(os.path.realpath(__file__))
                config_file = os.path.join(script_dir, "cloud_config.json")
                
                print(f"Saving updated configuration to {config_file}")
                with open(config_file, "w") as f:
                    json.dump(self.config, f, indent=2)
                print("Configuration saved successfully")
                return True
            return False
        except Exception as e:
            print(f"Error saving configuration: {str(e)}")
            return False
            
    def _format_dfm_response(self, analysis_result, part_name):
        """Format DFM analysis results into a user-friendly response with numbered list for better readability"""
        try:
            # Check if this is the new DFM endpoint response format
            if 'violations' in analysis_result:
                return self._format_new_dfm_response(analysis_result, part_name)
            else:
                # Use the existing formatter for the old response format
                return self._format_legacy_dfm_response(analysis_result, part_name)
        except Exception as e:
            print(f"Error formatting DFM response: {str(e)}")
            return f"Error formatting DFM analysis results: {str(e)}"
    
    def _format_new_dfm_response(self, analysis_result, part_name):
        """Format DFM analysis results from the new endpoint structure"""
        try:
            # Start with part name as a header
            response_text = f"DFM Analysis for {part_name}:\n\n"
            
            violations = analysis_result.get('violations', [])
            
            # Start numbered list
            item_num = 1
            
            # Add overall assessment
            if not violations:
                response_text += f"{item_num}. [OK] Overall: Excellent manufacturability\n"
            else:
                # Calculate overall severity based on highest severity score
                max_severity = max([v.get('severity_score', 0) for v in violations]) if violations else 0
                
                if max_severity >= 90:
                    response_text += f"{item_num}. 🚨 Overall: Critical manufacturability issues detected\n"
                elif max_severity >= 70:
                    response_text += f"{item_num}. ⚠️ Overall: Significant manufacturability issues detected\n"
                else:
                    response_text += f"{item_num}. ℹ️ Overall: Minor manufacturability issues detected\n"
            item_num += 1
            
            # Add process information
            process_name = "Unknown"
            
            # Try to get process from the response first
            if 'manufacturing_process' in analysis_result:
                process = analysis_result['manufacturing_process']
                if process == 'fdm':
                    process_name = "FDM 3D Printing"
                elif process == 'cnc':
                    process_name = "CNC Machining"
                elif process == 'injection_molding':
                    process_name = "Injection Molding"
            # Fall back to checking violations text
            elif violations and len(violations) > 0 and 'issue' in violations[0]:
                issue_text = violations[0]['issue'].lower()
                if 'fdm' in issue_text or '3d print' in issue_text or 'printing' in issue_text:
                    process_name = "FDM 3D Printing"
                    process = "fdm"
                elif 'cnc' in issue_text or 'machin' in issue_text or 'mill' in issue_text:
                    process_name = "CNC Machining"
                    process = "cnc"
            
            response_text += f"{item_num}. Manufacturing Process: {process_name}\n"
            item_num += 1
            
            # Add violations with severity indicators
            response_text += f"\n{item_num}. Manufacturability Issues:\n"
            item_num += 1
            
            if not violations:
                response_text += "   ✓ No specific manufacturability issues detected.\n"
            else:
                for i, violation in enumerate(violations, 1):
                    # Get severity and issue details
                    severity_score = violation.get('severity_score', 0)
                    issue = violation.get('issue', 'Unknown issue')
                    suggestion = violation.get('suggestion', '')
                    
                    # Choose emoji based on severity score
                    if severity_score >= 90:
                        emoji = "🚨"  # Red alert for critical issues
                    elif severity_score >= 70:
                        emoji = "⚠️"  # Warning for moderate issues
                    else:
                        emoji = "ℹ️"  # Info for minor issues
                        
                    # Format the issue and suggestion
                    issue_text = f"{emoji} {issue}"
                    if suggestion:
                        issue_text += f" - {suggestion}"
                    
                    response_text += f"   {i}. {issue_text}\n"
            
            return response_text
        except Exception as e:
            print(f"Error formatting new DFM response: {str(e)}")
            return f"Error formatting DFM analysis results: {str(e)}"
    
    def _format_legacy_dfm_response(self, analysis_result, part_name):
        """Format DFM analysis results from the legacy endpoint structure"""
        try:
            # Check if this is a 3D printing request by looking at the original query
            original_query = ''
            if 'original_query' in analysis_result:
                original_query = analysis_result.get('original_query', '').lower()
                print(f"DEBUG: Found original query in response: '{original_query}'")
            elif 'query_intent' in analysis_result:
                original_query = analysis_result.get('query_intent', {}).get('original_query', '').lower()
            
            # Force process detection from the original message
            process = ''
            if '3d print' in original_query or 'printed' in original_query or 'printing' in original_query:
                process = 'fdm'
                print("DEBUG: Forcing 3D printing specific formatting based on query")
            elif 'cnc' in original_query or 'machin' in original_query or 'mill' in original_query:
                process = 'cnc'
                print("DEBUG: Forcing CNC machining specific formatting based on query")
            
            # If we couldn't detect from query, try to get from response
            if not process:
                process = analysis_result.get('manufacturing_process', '')
                if not process and 'request_metadata' in analysis_result:
                    process = analysis_result.get('request_metadata', {}).get('manufacturing_process', '')
            
            # Default to generic if no process is specified
            process_name = "Manufacturing"
            
            # Force 3D printing specific response for 3D printing queries
            if '3d print' in original_query or 'printed' in original_query or 'printing' in original_query:
                process = 'fdm'
                process_name = "3D Printing (FDM)"
                print("DEBUG: Forcing 3D printing specific response format")
            # Force CNC machining specific response for machining queries
            elif 'cnc' in original_query or 'machin' in original_query or 'mill' in original_query:
                process = 'cnc'
                process_name = "CNC Machining"
                print("DEBUG: Forcing CNC machining specific response format")
            # Otherwise use the detected process
            elif process == 'fdm':
                process_name = "3D Printing (FDM)"
            elif process == 'cnc':
                process_name = "CNC Machining"
            elif process == 'injection_molding':
                process_name = "Injection Molding"
                
            # Start with part name and process as a header
            response_text = f"{process_name} Analysis for {part_name}:\n\n"
            
            # Get manufacturability index and complexity
            mfg_index = analysis_result.get('manufacturability_index', 0)
            complexity = analysis_result.get('manufacturing_features', {}).get('complexity_rating', 'Unknown')
            
            # Start numbered list
            item_num = 1
            
            # Add overall assessment as item #1 with process-specific wording
            if process == 'fdm':
                if mfg_index > 90:
                    response_text += f"{item_num}. [OK] Overall: Excellent 3D printability (Score: {mfg_index}/100)\n"
                elif mfg_index > 70:
                    response_text += f"{item_num}. ✓ Overall: Good 3D printability (Score: {mfg_index}/100)\n"
                elif mfg_index > 50:
                    response_text += f"{item_num}. ⚠️ Overall: Fair 3D printability (Score: {mfg_index}/100)\n"
                else:
                    response_text += f"{item_num}. 🚨 Overall: Poor 3D printability (Score: {mfg_index}/100)\n"
            elif process == 'cnc':
                if mfg_index > 90:
                    response_text += f"{item_num}. [OK] Overall: Excellent machinability (Score: {mfg_index}/100)\n"
                elif mfg_index > 70:
                    response_text += f"{item_num}. ✓ Overall: Good machinability (Score: {mfg_index}/100)\n"
                elif mfg_index > 50:
                    response_text += f"{item_num}. ⚠️ Overall: Fair machinability (Score: {mfg_index}/100)\n"
                else:
                    response_text += f"{item_num}. 🚨 Overall: Poor machinability (Score: {mfg_index}/100)\n"
            else:
                if mfg_index > 90:
                    response_text += f"{item_num}. [OK] Overall: Excellent manufacturability (Score: {mfg_index}/100)\n"
                elif mfg_index > 70:
                    response_text += f"{item_num}. ✓ Overall: Good manufacturability (Score: {mfg_index}/100)\n"
                elif mfg_index > 50:
                    response_text += f"{item_num}. ⚠️ Overall: Fair manufacturability (Score: {mfg_index}/100)\n"
                else:
                    response_text += f"{item_num}. 🚨 Overall: Poor manufacturability (Score: {mfg_index}/100)\n"
            item_num += 1
            
            # Add complexity as item #2 with process-specific context
            if process == 'fdm':
                response_text += f"{item_num}. Print Complexity: {complexity}\n"
                item_num += 1
                
                # Add 3D printing specific recommendations
                response_text += f"{item_num}. 3D Printing Recommendations:\n"
                response_text += f"   • Recommended material: PLA or ABS\n"
                response_text += f"   • Layer height: 0.2mm\n"
                response_text += f"   • Infill: 20-30%\n"
                if complexity.lower() == 'high':
                    response_text += f"   • Supports: Required\n"
                else:
                    response_text += f"   • Supports: Likely not needed\n"
            elif process == 'cnc':
                response_text += f"{item_num}. Machining Complexity: {complexity}\n"
                item_num += 1
                
                # Add CNC machining specific recommendations
                response_text += f"{item_num}. CNC Machining Recommendations:\n"
                response_text += f"   • Recommended material: Aluminum or mild steel\n"
                response_text += f"   • Minimum tool diameter: 3mm\n"
                if complexity.lower() == 'high':
                    response_text += f"   • Setup: Multi-axis machining recommended\n"
                else:
                    response_text += f"   • Setup: Standard 3-axis machining\n"
            else:
                response_text += f"{item_num}. Complexity: {complexity}\n"
            item_num += 1
            
            # Add design issues with severity indicators
            design_issues = analysis_result.get('design_issues', [])
            
            # For 3D printing queries, add specific 3D printing issues if none exist
            if process == 'fdm' and not design_issues:
                # Add some generic 3D printing considerations
                if analysis_result.get('dimensions', {}).get('z', 0) < 1.0:
                    design_issues.append("Layer height too thin - minimum 0.1mm recommended for FDM printing")
                elif analysis_result.get('dimensions', {}).get('z', 0) > 200:
                    design_issues.append("Model height exceeds typical build volume of many desktop 3D printers")
                
                # Add some generic 3D printing recommendations
                design_issues.append("Consider using PLA for easiest printing or ABS for better durability")
                design_issues.append("Print with 20% infill for a good balance of strength and material usage")
                design_issues.append("Orient the part for minimal support requirements")
            
            # Get the manufacturing process from the request or response
            process = analysis_result.get('manufacturing_process', '')
            if not process and 'request_metadata' in analysis_result:
                process = analysis_result.get('request_metadata', {}).get('manufacturing_process', '')
            
            # Process-specific section title
            if process == 'fdm':
                response_text += f"\n{item_num}. 3D Printing Considerations:\n"
            elif process == 'cnc':
                response_text += f"\n{item_num}. CNC Machining Considerations:\n"
            else:
                response_text += f"\n{item_num}. Manufacturability Issues:\n"
            item_num += 1
            
            if not design_issues:
                if process == 'fdm':
                    response_text += "   ✓ No specific 3D printing issues detected. The model appears to be printable.\n"
                    response_text += "   ℹ️ Recommended print settings: Layer height: 0.2mm, Infill: 20%, Support: No\n"
                elif process == 'cnc':
                    response_text += "   ✓ No specific CNC machining issues detected. The model appears to be machinable.\n"
                else:
                    response_text += "   ✓ No specific manufacturability issues detected.\n"
            else:
                for i, issue in enumerate(design_issues, 1):
                    # Determine severity based on keywords
                    severity = "info"
                    issue_text = issue.lower()
                    
                    if any(kw in issue_text for kw in ["critical", "severe", "cannot", "impossible", "fail"]):
                        severity = "critical"
                        emoji = "🚨"  # Red alert for critical issues
                    elif any(kw in issue_text for kw in ["warning", "recommend", "should", "consider", "improve"]):
                        severity = "warning"
                        emoji = "⚠️"  # Warning for moderate issues
                    else:
                        emoji = "ℹ️"  # Info for minor issues
                        
                    # Add process-specific context to generic issues
                    if process == 'fdm':
                        # Add 3D printing context to generic issues
                        if "thin" in issue_text or "thickness" in issue_text:
                            issue = f"{issue} (Critical for 3D printing - may cause print failure)"
                        elif "overhang" in issue_text:
                            issue = f"{issue} (May require supports during printing)"
                        elif "sharp" in issue_text or "corner" in issue_text:
                            issue = f"{issue} (Consider adding fillets for better print quality)"
                    elif process == 'cnc':
                        # Add CNC machining context to generic issues
                        if "internal corner" in issue_text or "sharp corner" in issue_text:
                            issue = f"{issue} (Not achievable with standard CNC tooling)"
                        elif "undercut" in issue_text:
                            issue = f"{issue} (May require multi-axis machining)"
                    
                    response_text += f"   {i}. {emoji} {issue}\n"
            
            # Add material recommendations
            materials = analysis_result.get('material_suggestions', [])
            if materials:
                response_text += f"\n{item_num}. Recommended Materials:\n"
                item_num += 1
                for i, material in enumerate(materials, 1):
                    response_text += f"   {i}. {material}\n"
            
            # Add process recommendations
            processes = analysis_result.get('process_recommendations', [])
            if processes:
                response_text += f"\n{item_num}. Recommended Manufacturing Processes:\n"
                for i, process in enumerate(processes, 1):
                    response_text += f"   {i}. {process}\n"
            
            return response_text
        except Exception as e:
            print(f"Error formatting DFM response: {str(e)}")
            return f"Error formatting DFM analysis results: {str(e)}"
    
    def get_connection_info(self):
        """Get detailed connection information"""
        return {
            "connected": self.connected,
            "quality": self.connection_quality,
            "latency": self.last_latency,
            "last_check": self.last_check_time,
            "last_error": self.last_error
        }

# Singleton cloud client instance
_cloud_client_instance = None

def get_cloud_client() -> CloudApiClient:
    """Get the singleton cloud client instance"""
    global _cloud_client_instance
    if _cloud_client_instance is None:
        _cloud_client_instance = CloudApiClient()
    return _cloud_client_instance

class StandaloneCoPilot(QtWidgets.QWidget):
    """Standalone Manufacturing Co-Pilot with built-in singleton pattern"""
    
    def __init__(self, parent=None):
        """Initialize the standalone co-pilot"""
        super().__init__(parent)
        
        # Connect to cloud
        self.cloud_client = get_cloud_client()
        self.cloud_connected = self.cloud_client.connected
        
        # Initialize NL CAD editor
        self.nl_cad_editor = NaturalLanguageCADEditor(self.cloud_client)
        print("Natural Language CAD Editor initialized")
        
        # Initialize Manufacturing Feature Manager for cloud features
        self.mfg_feature_manager = ManufacturingFeatureManager()
        print("Manufacturing Feature Manager initialized for cloud services")
        
        # Set up the UI
        self.setup_ui()
        
        # Register as connection listener
        self.cloud_client.add_connection_listener(self.update_status)
        
        # Update cloud status in UI with initial values
        conn_info = self.cloud_client.get_connection_info()
        self.update_status(
            conn_info["connected"],
            conn_info["quality"],
            conn_info["latency"]
        )
        
        # Set up periodic connection check
        self.connection_timer = QtCore.QTimer()
        self.connection_timer.timeout.connect(self.check_connection)
        self.connection_timer.start(60000)  # Check every minute
    
    def setup_ui(self):
        """Set up the user interface"""
        # Set window title and size
        self.setWindowTitle("Axis 5")
        self.resize(500, 600)
        
        # Initialize chat entries list
        self.chat_entries = []
        print("DEBUG: Initialized chat_entries list in setup_ui")
        
        # Set dark theme for the entire widget
        self.setStyleSheet("""
            QWidget {
                background-color: #333333;
                color: #E0E0E0;
            }
            QPushButton {
                background-color: #444444;
                color: #E0E0E0;
                border: 1px solid #555555;
                border-radius: 4px;
                padding: 5px;
                min-height: 25px;
            }
            QPushButton:hover {
                background-color: #555555;
            }
            QPushButton:pressed {
                background-color: #666666;
            }
            QLabel {
                color: #E0E0E0;
            }
            QGroupBox {
                border: 1px solid #555555;
                border-radius: 5px;
                margin-top: 10px;
                padding-top: 10px;
                color: #E0E0E0;
            }
            QGroupBox::title {
                subcontrol-origin: margin;
                subcontrol-position: top center;
                padding: 0 5px;
            }
        """)
        
        # Create main layout
        layout = QtWidgets.QVBoxLayout()
        self.setLayout(layout)
        
        # Add header with logo and status
        header_layout = QtWidgets.QHBoxLayout()
        
        # Logo and title
        logo_label = QtWidgets.QLabel("🔧")
        logo_label.setStyleSheet("font-size: 24px;")
        title_label = QtWidgets.QLabel("Manufacturing Co-Pilot")
        title_label.setStyleSheet("font-size: 16px; font-weight: bold;")
        
        # Status indicator
        self.status_layout = QtWidgets.QHBoxLayout()
        self.status_indicator = QtWidgets.QLabel("●")
        self.status_indicator.setStyleSheet("color: red;")
        self.status_text = QtWidgets.QLabel("Cloud: Disconnected")
        self.status_layout.addWidget(self.status_indicator)
        self.status_layout.addWidget(self.status_text)
        
        # Create tooltip with detailed connection info
        self.status_widget = QtWidgets.QWidget()
        self.status_widget.setLayout(self.status_layout)
        self.status_widget.setToolTip("Cloud connection status")
        
        # Add to header layout
        header_layout.addWidget(logo_label)
        header_layout.addWidget(title_label)
        header_layout.addStretch()
        header_layout.addWidget(self.status_widget)
        
        # Make status clickable to retry connection
        self.status_widget.setCursor(QtCore.Qt.PointingHandCursor)
        self.status_widget.mousePressEvent = self.retry_connection
        
        # Add header to main layout
        layout.addLayout(header_layout)
        
        # Add chat history area
        self.chat_history = QtWidgets.QTextEdit()
        self.chat_history.setReadOnly(True)
        self.chat_history.setMinimumHeight(300)
        
        # Set dark theme colors for chat history - ensure dark background and light text
        self.chat_history.setStyleSheet("""
            QTextEdit {
                background-color: #1E1E1E;
                color: #E0E0E0;
                border: 1px solid #555555;
                border-radius: 4px;
                padding: 4px;
            }
            QTextEdit QWidget {
                background-color: #1E1E1E;
                color: #E0E0E0;
            }
            QScrollBar:vertical {
                background-color: #2D2D2D;
                width: 14px;
                margin: 0px;
            }
            QScrollBar::handle:vertical {
                background-color: #555555;
                min-height: 20px;
                border-radius: 7px;
            }
            QScrollBar::add-line:vertical, QScrollBar::sub-line:vertical {
                height: 0px;
            }
        """)
        
        layout.addWidget(self.chat_history)
        
        # Add input area with send button
        input_layout = QtWidgets.QHBoxLayout()
        
        self.input_field = QtWidgets.QTextEdit()
        self.input_field.setPlaceholderText("Ask about manufacturing...")
        self.input_field.setMaximumHeight(100)
        
        # Set dark theme colors for input field - ensure dark background and light text
        self.input_field.setStyleSheet("""
            QTextEdit {
                background-color: #1E1E1E;
                color: #E0E0E0;
                border: 1px solid #555555;
                border-radius: 4px;
                padding: 4px;
            }
            QTextEdit QWidget {
                background-color: #1E1E1E;
                color: #E0E0E0;
            }
            QScrollBar:vertical {
                background-color: #2D2D2D;
                width: 14px;
                margin: 0px;
            }
            QScrollBar::handle:vertical {
                background-color: #555555;
                min-height: 20px;
                border-radius: 7px;
            }
        """)
        
        input_layout.addWidget(self.input_field)
        
        self.send_button = QtWidgets.QPushButton("Send")
        self.send_button.clicked.connect(self.send_message)
        self.send_button.setMinimumHeight(80)
        input_layout.addWidget(self.send_button)
        
        layout.addLayout(input_layout)
        
        # Connect enter key to send message
        self.input_field.installEventFilter(self)
        
        # Add buttons
        button_layout = QtWidgets.QHBoxLayout()
        
        self.analyze_button = QtWidgets.QPushButton("Analyze")
        self.analyze_button.clicked.connect(self.on_analyze_clicked)
        
        self.suggestions_button = QtWidgets.QPushButton("Suggestions")
        self.suggestions_button.clicked.connect(self.on_suggestions_clicked)
        
        self.clear_button = QtWidgets.QPushButton("Clear")
        self.clear_button.clicked.connect(self.on_clear_clicked)
        
        button_layout.addWidget(self.analyze_button)
        button_layout.addWidget(self.suggestions_button)
        button_layout.addWidget(self.clear_button)
        
        layout.addLayout(button_layout)
        
        # Add cloud manufacturing features section
        self.add_manufacturing_features_ui(layout)
        
        # Add initial message
        self.add_system_message("Welcome to the Manufacturing Co-Pilot!")
        self.add_system_message("Ask questions about manufacturing or CAD design.")
        
        # Add cloud status message
        if self.cloud_connected:
            self.add_system_message(f"Connected to cloud service at {self.cloud_client.api_url}")
        else:
            self.add_system_message(f"Failed to connect to cloud service: {self.cloud_client.last_error}")
    
    def eventFilter(self, obj, event):
        """Handle events for input field"""
        if obj is self.input_field and event.type() == QtCore.QEvent.KeyPress:
            if event.key() == QtCore.Qt.Key_Return and not event.modifiers() & QtCore.Qt.ShiftModifier:
                self.send_message()
                return True
        return super().eventFilter(obj, event)
    
    def send_message(self):
        """Send a message to the cloud service"""
        message = self.input_field.toPlainText().strip()
        if not message:
            return
        
        # Add user message to chat history
        self.add_user_message(message)
        
        # Clear input field
        self.input_field.clear()
        
        # Show processing indicator
        self.add_system_message("Processing...")
        
        # Try text-to-CAD first (if available)
        if hasattr(self, 'nl_cad_editor') and hasattr(self.nl_cad_editor, 'text_to_cad') and self.nl_cad_editor.text_to_cad.is_text_to_cad_request(message):
            self.process_cad_command(message)
        # Check if this is a regular CAD command
        elif self.is_cad_command(message):
            self.process_cad_command(message)
        else:
            # Use Axis 5 Claude AI for conversational CAD generation and manufacturing intelligence
            try:
                # Remove processing indicator
                self.remove_last_processing_message()
                
                # Use Claude AI processor for advanced conversational processing
                if hasattr(self, 'ai_processor') and self.ai_processor:
                    print(f"🤖 Axis 5 processing conversational request: {message[:50]}...")
                    ai_response = self.ai_processor.process_advanced_command(message)
                    
                    if ai_response and ai_response.get('success'):
                        response_text = ai_response.get('response', 'No response received')
                        
                        # Check if Claude generated FreeCAD code for CAD generation
                        freecad_code = ai_response.get('freecad_code')
                        if freecad_code:
                            print(f"[OK] Axis 5 generated FreeCAD code: {len(freecad_code)} chars")
                            # Execute the FreeCAD code for CAD generation
                            try:
                                exec(freecad_code)
                                if FreeCAD.ActiveDocument:
                                    FreeCAD.ActiveDocument.recompute()
                                if hasattr(FreeCADGui, 'ActiveDocument') and FreeCADGui.ActiveDocument:
                                    FreeCADGui.ActiveDocument.ActiveView.fitAll()
                                response_text += "\n\n[OK] CAD model generated successfully and visible in 3D view!"
                            except Exception as code_err:
                                print(f"Error executing Axis 5's FreeCAD code: {str(code_err)}")
                                response_text += f"\n\n⚠️ Error executing generated CAD code: {str(code_err)}"
                        
                        # Add Axis 5's conversational response to chat
                        source = ai_response.get('source', 'ai')
                        if source == 'claude_conversational':
                            self.add_assistant_message(f"🤖 Axis 5: {response_text}")
                        else:
                            self.add_assistant_message(response_text)
                    else:
                        error_msg = ai_response.get('error', 'Unknown error') if ai_response else 'No response'
                        print(f"Axis 5 processing failed: {error_msg}")
                        # Fallback to cloud service
                        response = self.cloud_client.get_chat_response(message)
                        
                        # Extract response text
                        if "response" in response:
                            response_text = response["response"]
                        elif "error" in response:
                            response_text = f"Error: {response['error']}"
                        else:
                            print(f"Debug: Received empty response from cloud: {response}")
                            response_text = "I'm processing your request locally."
                        
                        # Add fallback response
                        self.add_assistant_message(response_text)
                else:
                    # Fallback to cloud service if AI processor not available
                    response = self.cloud_client.get_chat_response(message)
                    
                    # Extract response text
                    if "response" in response:
                        response_text = response["response"]
                    elif "error" in response:
                        response_text = f"Error: {response['error']}"
                    else:
                        print(f"Debug: Received empty response from cloud: {response}")
                        response_text = "I'm processing your request locally."
                    
                    # Add fallback response
                    self.add_assistant_message(response_text)
                
            except Exception as e:
                # Remove processing indicator
                self.remove_last_processing_message()
                
                # Add error message
                self.add_system_message(f"Axis 5 Error: {str(e)}")
                print(f"Error in Axis 5 processing: {e}")
                traceback.print_exc()
    
    def is_cad_command(self, text):
        """Check if the text is a CAD command"""
        cad_indicators = [
            'create', 'make', 'add', 'generate',
            'box', 'cylinder', 'sphere', 'cube',
            'bracket', 'gear', 'housing', 'shaft',
            'extrude', 'extend', 'pull', 'fillet', 'round'
        ]
        
        text_lower = text.lower()
        return any(indicator in text_lower for indicator in cad_indicators)
    
    def process_cad_command(self, text):
        """Process a CAD command using the NL CAD editor"""
        try:
            # Remove processing indicator
            self.remove_last_processing_message()
            
            # Add system message
            self.add_system_message(f"Creating CAD model from: '{text}'")
            
            # Update status indicator
            self.cloud_feature_status.setText("Processing Text-to-CAD request...")
            
            # Process command with NL CAD editor
            result = self.nl_cad_editor.process_command(text)
            
            if result['success']:
                # Add success message
                self.add_system_message(f"[OK] {result['message']}")
                
                # Check for engineering analysis from Text-to-CAD
                if 'engineering_analysis' in result and result['engineering_analysis']:
                    # Format engineering analysis as a detailed message
                    analysis_message = f"I've created the CAD model based on your description. You can see it in the 3D view.\n\n"
                    analysis_message += f"**Engineering Analysis:**\n{result['engineering_analysis']}"
                    self.add_assistant_message(analysis_message)
                else:
                    # Add standard assistant message with details
                    self.add_assistant_message(f"I've created the CAD model based on your description. You can see it in the 3D view.")
            else:
                # Add error message
                self.add_system_message(f"❌ {result['message']}")
                
                # Add assistant message with error
                self.add_assistant_message(f"I couldn't create the CAD model. {result['message']}")
            
        except Exception as e:
            # Add error message
            self.add_system_message(f"Error processing CAD command: {str(e)}")
            traceback.print_exc()
        finally:
            # Reset status indicator
            self.cloud_feature_status.setText("Ready")
    
    def update_status(self, connected, quality="unknown", latency=0):
        """Update the cloud connection status indicator"""
        if connected:
            # Set color based on connection quality
            if quality == "excellent":
                self.status_indicator.setStyleSheet("color: #00AA00;")  # Bright green
                status_text = "Cloud: Excellent"
            elif quality == "good":
                self.status_indicator.setStyleSheet("color: #00CC00;")  # Green
                status_text = "Cloud: Good"
            elif quality == "fair":
                self.status_indicator.setStyleSheet("color: #CCCC00;")  # Yellow
                status_text = "Cloud: Fair"
            elif quality == "poor":
                self.status_indicator.setStyleSheet("color: #CC6600;")  # Orange
                status_text = "Cloud: Poor"
            else:
                self.status_indicator.setStyleSheet("color: #00CC00;")  # Default green
                status_text = "Cloud: Connected"
                
            self.status_text.setText(status_text)
            self.cloud_connected = True
            
            # Update tooltip with detailed info
            tooltip = f"Cloud Status: {quality.title()}\nLatency: {latency}ms"
            self.status_widget.setToolTip(tooltip)
        else:
            self.status_indicator.setStyleSheet("color: red;")
            self.status_text.setText("Cloud: Disconnected")
            self.cloud_connected = False
            self.status_widget.setToolTip("Cloud connection failed. Click to retry.")
    
    def retry_connection(self, event):
        """Retry cloud connection when status indicator is clicked"""
        self.add_system_message("Retrying cloud connection...")
        success = self.cloud_client.test_connection()
        if success:
            self.add_system_message("Cloud connection restored!")
        else:
            self.add_system_message(f"Cloud connection failed: {self.cloud_client.last_error}")
    
    def check_connection(self):
        """Periodically check cloud connection"""
        # Only run check if more than 5 minutes since last check
        current_time = time.time()
        if current_time - self.cloud_client.last_check_time > 300:
            print("Performing periodic connection check")
            self.cloud_client.test_connection()
    
    def add_system_message(self, message):
        """Add a system message to the chat history"""
        print(f"DEBUG: add_system_message called with message: {message}")
        timestamp = datetime.now().strftime("%H:%M")
        chat_entry = f"<b>[{timestamp}] System:</b> {message}"
        
        # Initialize chat_entries as a list if it doesn't exist
        if not hasattr(self, 'chat_entries') or self.chat_entries is None:
            print("DEBUG: Initializing chat_entries as a list in add_system_message")
            self.chat_entries = []
            
        # Ensure chat_entries is a list before appending
        if not isinstance(self.chat_entries, list):
            print(f"DEBUG: Converting chat_entries from {type(self.chat_entries)} to list in add_system_message")
            self.chat_entries = [str(self.chat_entries)]
            
        self.chat_entries.append(chat_entry)
        print("DEBUG: Updated chat_entries with system message, refreshing display")
        # Force refresh of the chat display
        self._update_chat_display()
        
    def remove_last_processing_message(self):
        """Remove the last 'Processing...' message from chat history"""
        print("DEBUG: Removing last processing message")
        
        # Initialize chat_entries if needed
        if not hasattr(self, 'chat_entries') or not isinstance(self.chat_entries, list):
            print("DEBUG: No chat_entries list to remove from")
            return
            
        # Find and remove the last processing message
        for i in range(len(self.chat_entries) - 1, -1, -1):
            if "Processing..." in self.chat_entries[i]:
                print(f"DEBUG: Found processing message at index {i}")
                self.chat_entries.pop(i)
                print("DEBUG: Removed processing message, refreshing display")
                self._update_chat_display()
                return
                
        print("DEBUG: No processing message found to remove")
    
    def add_user_message(self, message):
        """Add a user message to the chat history"""
        print(f"DEBUG: add_user_message called with message: {message}")
        timestamp = datetime.now().strftime("%H:%M")
        chat_entry = f"<b>[{timestamp}] You:</b> {message}"
        
        # Initialize chat_entries as a list if it doesn't exist
        if not hasattr(self, 'chat_entries') or self.chat_entries is None:
            print("DEBUG: Initializing chat_entries as a list in add_user_message")
            self.chat_entries = []
            
        # Ensure chat_entries is a list before appending
        if not isinstance(self.chat_entries, list):
            print(f"DEBUG: Converting chat_entries from {type(self.chat_entries)} to list in add_user_message")
            self.chat_entries = [str(self.chat_entries)]
            
        self.chat_entries.append(chat_entry)
        print("DEBUG: Updated chat_entries with user message, refreshing display")
        # Force refresh of the chat display
        self._update_chat_display()
    
    def add_assistant_message(self, message):
        """Add an assistant message to the chat history"""
        print(f"DEBUG: add_assistant_message called with message length: {len(message)}")
        timestamp = datetime.now().strftime("%H:%M")
        chat_entry = f"<b>[{timestamp}] Axis 5:</b> {message}"
        print(f"DEBUG: Adding entry to chat_entries, length: {len(chat_entry)}")
        
        # Initialize chat_entries as a list if it doesn't exist
        if not hasattr(self, 'chat_entries') or self.chat_entries is None:
            print("DEBUG: Initializing chat_entries as a list")
            self.chat_entries = []
            
        # Ensure chat_entries is a list before appending
        if not isinstance(self.chat_entries, list):
            print(f"DEBUG: Converting chat_entries from {type(self.chat_entries)} to list")
            self.chat_entries = [str(self.chat_entries)]
            
        self.chat_entries.append(chat_entry)
        print("DEBUG: Updated chat_entries, refreshing display")
        # Force refresh of the chat display
        self._update_chat_display()
        
    def _update_chat_display(self):
        """Update the chat display with the current chat history"""
        print("DEBUG: _update_chat_display called")
        
        try:
            # Check if chat_entries attribute exists and is a list
            if not hasattr(self, 'chat_entries'):
                print("DEBUG: Initializing chat_entries as a list")
                self.chat_entries = []
            
            # Ensure chat_entries is a list
            if not isinstance(self.chat_entries, list):
                print(f"DEBUG: Converting chat_entries from {type(self.chat_entries)} to list")
                self.chat_entries = [str(self.chat_entries)]
            
            # Check if chat_history attribute exists and is a QTextEdit widget
            if hasattr(self, 'chat_history') and isinstance(self.chat_history, QtWidgets.QTextEdit):
                print("DEBUG: chat_history is a QTextEdit widget")
                print(f"DEBUG: Found {len(self.chat_entries)} chat entries")
                
                # Join all entries with proper HTML line breaks
                html_content = "<html><body>"
                for entry in self.chat_entries:
                    html_content += entry + "<br><br>"
                html_content += "</body></html>"
                
                # Set the HTML content to the widget
                print(f"DEBUG: Setting HTML content of length {len(html_content)}")
                self.chat_history.setHtml(html_content)
                print("DEBUG: Updated chat_history widget with HTML content")
                
                # Scroll to bottom
                scrollbar = self.chat_history.verticalScrollBar()
                scrollbar.setValue(scrollbar.maximum())
                print("DEBUG: Scrolled to bottom of chat_history")
            else:
                print("DEBUG: chat_history is not a QTextEdit widget, outputting to console instead")
                print("\n=== CHAT HISTORY ===\n")
                for entry in self.chat_entries:
                    # Strip HTML tags for console output
                    plain_text = re.sub('<[^<]+?>', '', entry)
                    print(plain_text)
                print("\n=== END CHAT HISTORY ===\n")
        except Exception as e:
            print(f"ERROR: Failed to update chat display: {str(e)}")
            traceback.print_exc()
            
    def on_clear_clicked(self):
        """Handle clear button click"""
        self.chat_history.clear()
        self.add_system_message("Chat history cleared.")

    def add_manufacturing_features_ui(self, layout):
        """Add cloud manufacturing features UI elements"""
        # Create group box for manufacturing features
        mfg_group = QtWidgets.QGroupBox("Cloud Manufacturing Features")
        mfg_layout = QtWidgets.QVBoxLayout()
        
    def on_analyze_clicked(self):
        """Handle analyze button click - now runs full DFM analysis with professional overlays"""
        self.add_system_message("Running DFM analysis with professional overlays...")
        try:
            # Check if there's an active document
            if FreeCAD.ActiveDocument:
                doc_name = FreeCAD.ActiveDocument.Name
                objects = FreeCAD.ActiveDocument.Objects
                object_count = len(objects)
                
                if object_count == 0:
                    self.add_system_message("No objects found to analyze")
                    self.add_assistant_message("Please create or import a CAD object first, then click Analyze to see DFM overlays with tooltips.")
                    return
                
                # Run full DFM analysis with professional overlays
                self.add_assistant_message(f"🔍 Analyzing {object_count} objects in '{doc_name}' for manufacturing issues...")
                
                # Run DFM analysis using the manufacturing feature manager
                result = self.mfg_feature_manager.analyze_dfm(
                    manufacturing_process="3d_printing",  # Default process
                    material="pla",                       # Default material
                    production_volume=1,                  # Default volume
                    advanced_analysis=True                # Enable advanced analysis
                )
                
                if result and result.get('success'):
                    data = result.get('data', {})
                    issues = data.get('issues', [])
                    score = data.get('manufacturability_score', 0)
                    
                    self.add_assistant_message(f"[OK] DFM Analysis Complete!\n\n"
                                             f"📊 Manufacturability Score: {score}/100\n"
                                             f"🔍 Found {len(issues)} manufacturing issues\n\n"
                                             f"🎯 **Professional overlays with tooltips are now active!**\n"
                                             f"• **Hover** over colored areas to see issue details\n"
                                             f"• **Click** on overlays to pin/unpin tooltips\n"
                                             f"• Overlays automatically follow object movements")
                    
                    if issues:
                        issues_text = "\n".join([f"• {issue.get('title', 'Issue')}: {issue.get('description', 'No description')}" 
                                               for issue in issues[:5]])  # Show first 5 issues
                        if len(issues) > 5:
                            issues_text += f"\n... and {len(issues) - 5} more issues (see overlays)"
                        self.add_assistant_message(f"🚨 **Manufacturing Issues Found:**\n{issues_text}")
                else:
                    # Fallback to basic analysis if DFM fails
                    analysis_text = f"Active document: {doc_name} with {object_count} objects\n"
                    for obj in objects:
                        if hasattr(obj, 'Shape'):
                            volume = obj.Shape.Volume
                            bbox = obj.Shape.BoundBox
                            dimensions = f"{bbox.XLength:.1f}x{bbox.YLength:.1f}x{bbox.ZLength:.1f}"
                            analysis_text += f"- {obj.Label}: {obj.TypeId}, Volume: {volume:.1f} mm³, Size: {dimensions} mm\n"
                        else:
                            analysis_text += f"- {obj.Label}: {obj.TypeId}\n"
                    
                    self.add_assistant_message(f"Here's my basic analysis:\n\n{analysis_text}\n\n"
                                             f"💡 **Tip:** For DFM overlays with tooltips, ensure you have a mesh or solid object selected.")
            else:
                self.add_system_message("No active document found")
                self.add_assistant_message("There is no active document to analyze. Please create or open a document first.")
        except Exception as e:
            self.add_system_message(f"Error analyzing model: {str(e)}")
            self.add_assistant_message(f"❌ Analysis failed: {str(e)}\n\n"
                                     f"💡 **Quick Test:** Try creating a simple cube first:\n"
                                     f"```python\n"
                                     f"import FreeCAD, Part\n"
                                     f"doc = FreeCAD.newDocument()\n"
                                     f"cube = doc.addObject('Part::Box', 'TestCube')\n"
                                     f"cube.Length = 20\n"
                                     f"cube.Width = 15\n"
                                     f"cube.Height = 10\n"
                                     f"doc.recompute()\n"
                                     f"```\n"
                                     f"Then click Analyze again!")
            traceback.print_exc()
    
    def on_suggestions_clicked(self):
        """Handle suggestions button click"""
        self.add_system_message("Generating CAD suggestions...")
        
        # Suggest some CAD commands
        suggestions = [
            "Create a box 100x50x20",
            "Make a cylinder with diameter 30 and height 50",
            "Create a bracket with mounting holes",
            "Generate a gear with 20 teeth"
        ]
        
        # Add suggestions to chat
        self.add_assistant_message("Here are some CAD commands you can try:\n\n" + 
                               "\n".join([f"- {s}" for s in suggestions]) + 
                               "\n\nJust type one of these commands or create your own!")
        
        # Set a random suggestion in the input field
        self.input_field.setText(random.choice(suggestions))
    
    def on_clear_clicked(self):
        """Handle clear button click"""
        self.chat_history.clear()
        self.add_system_message("Chat history cleared.")
        
    def add_manufacturing_features_ui(self, layout):
        """Add cloud manufacturing features UI elements"""
        # Create group box for manufacturing features
        mfg_group = QtWidgets.QGroupBox("Cloud Manufacturing Features")
        mfg_layout = QtWidgets.QVBoxLayout()
        
        # Add description label
        desc_label = QtWidgets.QLabel("Access cloud-based manufacturing intelligence:")
        mfg_layout.addWidget(desc_label)
        
        # Create button grid layout
        button_grid = QtWidgets.QGridLayout()
        
        # DFM Analysis button
        self.dfm_button = QtWidgets.QPushButton("Advanced DFM Analysis")
        self.dfm_button.setToolTip("Analyze design for manufacturability using industry-grade DFM engine")
        self.dfm_button.clicked.connect(self.on_dfm_clicked)
        button_grid.addWidget(self.dfm_button, 0, 0)
        
        # Cost Estimation button
        self.cost_button = QtWidgets.QPushButton("Cost Estimation")
        self.cost_button.setToolTip("Estimate manufacturing costs")
        self.cost_button.clicked.connect(self.on_cost_clicked)
        button_grid.addWidget(self.cost_button, 0, 1)
        
        # Tool Recommendations button
        self.tools_button = QtWidgets.QPushButton("Tool Recommendations")
        self.tools_button.setToolTip("Get tool and machining recommendations")
        self.tools_button.clicked.connect(self.on_tools_clicked)
        button_grid.addWidget(self.tools_button, 1, 0)
        
        # Manufacturing Method Comparison button
        self.compare_button = QtWidgets.QPushButton("Compare Methods")
        self.compare_button.setToolTip("Compare different manufacturing methods")
        self.compare_button.clicked.connect(self.on_compare_clicked)
        button_grid.addWidget(self.compare_button, 1, 1)
        
        # Show Problem Area button (RESTORED HEATMAP OVERLAY FEATURE)
        # Initially hidden - only shown after DFM analysis completes
        self.show_problems_button = QtWidgets.QPushButton("Show Problem Areas")
        self.show_problems_button.setToolTip("Visualize manufacturing problem areas with colored overlays on the CAD model")
        self.show_problems_button.clicked.connect(self.on_show_problems_clicked)
        self.show_problems_button.setVisible(False)  # Hidden by default
        button_grid.addWidget(self.show_problems_button, 2, 0)
        
        # Hide Problem Area button
        # Initially hidden - only shown after problem areas are displayed
        self.hide_problems_button = QtWidgets.QPushButton("Hide Problem Areas")
        self.hide_problems_button.setToolTip("Remove manufacturing problem area overlays from the CAD model")
        self.hide_problems_button.clicked.connect(self.on_hide_problems_clicked)
        self.hide_problems_button.setVisible(False)  # Hidden by default
        button_grid.addWidget(self.hide_problems_button, 2, 1)
        
        # Add button grid to layout
        mfg_layout.addLayout(button_grid)
        
        # Add status indicator for cloud features
        cloud_status_layout = QtWidgets.QHBoxLayout()
        self.cloud_feature_status = QtWidgets.QLabel("Ready")
        cloud_status_layout.addWidget(QtWidgets.QLabel("Status:"))
        cloud_status_layout.addWidget(self.cloud_feature_status)
        cloud_status_layout.addStretch()
        mfg_layout.addLayout(cloud_status_layout)
        
        # Set the layout to the group box
        mfg_group.setLayout(mfg_layout)
        
        # Add the group box to the main layout
        layout.addWidget(mfg_group)
    
    def on_dfm_clicked(self):
        """Handle DFM analysis button click with advanced options"""
        self.add_system_message("Preparing advanced DFM analysis...")
        try:
            # Check if there's an active document
            if not FreeCAD.ActiveDocument:
                self.add_system_message("No active document found")
                self.add_assistant_message("Please open or create a model before running DFM analysis.")
                return
            
            # Create dialog for advanced DFM options
            dialog = QtWidgets.QDialog(self)
            dialog.setWindowTitle("Advanced DFM Analysis Options")
            dialog.setMinimumWidth(400)
            
            # Create form layout for options
            form_layout = QtWidgets.QFormLayout(dialog)
            
            # Manufacturing process selection
            process_combo = QtWidgets.QComboBox()
            process_combo.addItems([
                "3D Printing (FDM)", 
                "CNC Machining", 
                "Injection Molding",
                "Sheet Metal Forming",
                "Die Casting"
            ])
            form_layout.addRow("Manufacturing Process:", process_combo)
            
            # Material selection
            material_combo = QtWidgets.QComboBox()
            material_combo.addItems([
                "PLA", "ABS", "Nylon",  # 3D Printing materials
                "Aluminum", "Steel", "Brass",  # Metals
                "Polypropylene", "ABS", "Polycarbonate"  # Injection molding materials
            ])
            form_layout.addRow("Material:", material_combo)
            
            # Production volume
            volume_spin = QtWidgets.QSpinBox()
            volume_spin.setRange(1, 1000000)
            volume_spin.setValue(100)
            volume_spin.setSingleStep(10)
            form_layout.addRow("Production Volume:", volume_spin)
            
            # Advanced analysis checkbox
            advanced_check = QtWidgets.QCheckBox("Enable advanced analysis")
            advanced_check.setChecked(True)
            advanced_check.setToolTip("Includes detailed cost analysis and alternative process recommendations")
            form_layout.addRow("", advanced_check)
            
            # Add buttons
            button_box = QtWidgets.QDialogButtonBox(
                QtWidgets.QDialogButtonBox.Ok | QtWidgets.QDialogButtonBox.Cancel
            )
            button_box.accepted.connect(dialog.accept)
            button_box.rejected.connect(dialog.reject)
            form_layout.addRow(button_box)
            
            # Show dialog and get results
            if dialog.exec_() != QtWidgets.QDialog.Accepted:
                self.add_system_message("DFM analysis cancelled")
                return
            
            # Get selected options
            process_text = process_combo.currentText()
            material_text = material_combo.currentText().lower()
            production_volume = volume_spin.value()
            advanced_analysis = advanced_check.isChecked()
            
            # Map process text to process code
            process_map = {
                "3D Printing (FDM)": "3d_printing",
                "CNC Machining": "cnc_machining",
                "Injection Molding": "injection_molding",
                "Sheet Metal Forming": "sheet_metal",
                "Die Casting": "die_casting"
            }
            process_code = process_map.get(process_text, "3d_printing")
            
            # Update status
            self.cloud_feature_status.setText("Processing advanced DFM analysis...")
            self.add_system_message(f"Running advanced DFM analysis for {process_text} with {material_text} material...")
            
            # Run DFM analysis using the manufacturing feature manager with advanced options
            result = self.mfg_feature_manager.analyze_dfm(
                manufacturing_process=process_code,
                material=material_text,
                production_volume=production_volume,
                advanced_analysis=advanced_analysis
            )
            
            if result and result.get('success'):
                print("DEBUG: DFM analysis successful, processing UI display")
                print(f"DEBUG: Result keys: {list(result.keys())}")
                
                # Get the data from the result
                data = result.get('data', {})
                print(f"DEBUG: Data keys in result: {list(data.keys())}")
                
                # Try to get data from the transformed format first
                score = data.get('manufacturability_score', 0)
                issues = data.get('issues', [])
                recommendations = data.get('recommendations', [])
                report_text = data.get('report_text', '')
                
                # If we don't have a score, try to get it from the original format
                if score == 0 and 'overall_manufacturability_score' in data:
                    score = data.get('overall_manufacturability_score', 0)
                    print("DEBUG: Using overall_manufacturability_score from transformed data")
                    
                # If we don't have issues, try to get them from the original format
                if not issues and 'manufacturing_issues' in data:
                    issues = data.get('manufacturing_issues', [])
                    print(f"DEBUG: Using manufacturing_issues from transformed data: {issues}")
                    
                # If we don't have issues, try to get them from design_issues
                print(f"DEBUG: Before design_issues check - issues length: {len(issues)}")
                if not issues and 'design_issues' in data:
                    design_issues = data.get('design_issues', [])
                    print(f"DEBUG: Found {len(design_issues)} design_issues: {design_issues}")
                    
                    # Convert design_issues to our format
                    for issue in design_issues:
                        if isinstance(issue, str):
                            print(f"DEBUG: Converting string issue: {issue}")
                            issues.append({
                                'severity': 'medium',
                                'description': issue
                            })
                        elif isinstance(issue, dict):
                            print(f"DEBUG: Adding dict issue: {issue}")
                            issues.append(issue)
                    
                    print(f"DEBUG: Converted {len(issues)} design_issues to issues format")
                elif 'design_issues' in data:
                    print(f"DEBUG: Skipping design_issues conversion - already have {len(issues)} issues")
                else:
                    print("DEBUG: No design_issues found in data")
                    
                # If we don't have recommendations, try to get them from the original format
                if not recommendations and 'expert_recommendations' in data:
                    recommendations = data.get('expert_recommendations', [])
                    print("DEBUG: Using expert_recommendations from transformed data")
                
                # Store the analysis data for visualization (CRITICAL FIX)
                self.last_analysis = {
                    'manufacturing_issues': issues,
                    'design_issues': data.get('design_issues', []),
                    'overall_manufacturability_score': score,
                    'overall_rating': data.get('overall_rating', ''),
                    'primary_process': data.get('primary_process', ''),
                    'alternative_processes': data.get('alternative_processes', []),
                    'expert_recommendations': recommendations
                }
                print(f"DEBUG: Set last_analysis with {len(issues)} manufacturing_issues for visualization")
                
                print(f"DEBUG: UI received score: {score}")
                print(f"DEBUG: UI received {len(issues)} issues")
                print(f"DEBUG: UI received {len(recommendations)} recommendations")
                print(f"DEBUG: UI received report_text of length {len(report_text)}")
                if report_text:
                    print(f"DEBUG: First 100 chars of report_text: {report_text[:100]}")
                else:
                    print("DEBUG: No report_text received, generating from available data")
                    # Generate comprehensive report text from all available data
                    report_lines = []
                    report_lines.append("=== DESIGN FOR MANUFACTURING ANALYSIS ===")
                    report_lines.append(f"Manufacturability Score: {score}/100")
                    
                    # Add overall rating if available
                    overall_rating = data.get('overall_rating', '')
                    if overall_rating:
                        report_lines.append(f"Overall Rating: {overall_rating}")
                    report_lines.append("")
                    
                    # Add geometry summary if available
                    geometry_summary = data.get('geometry_summary', {})
                    if geometry_summary:
                        report_lines.append("--- Geometry Analysis ---")
                        if 'volume' in geometry_summary:
                            report_lines.append(f"Volume: {geometry_summary['volume']:.2f} mm³")
                        if 'faces' in geometry_summary:
                            report_lines.append(f"Faces: {geometry_summary['faces']}")
                        if 'holes' in geometry_summary:
                            report_lines.append(f"Holes: {geometry_summary['holes']}")
                        if 'fillets' in geometry_summary:
                            report_lines.append(f"Fillets: {geometry_summary['fillets']}")
                        report_lines.append("")
                    
                    # Add issues with red color (HTML formatting)
                    report_lines.append(f"--- Manufacturing Issues ({len(issues)}) ---")
                    # Apply red color to ALL manufacturing issues text
                    if issues:
                        for issue in issues:
                            if isinstance(issue, dict):
                                description = issue.get('description', 'Unknown issue')
                                severity = issue.get('severity', 'medium')
                                recommendation = issue.get('recommendation', '')
                                
                                # Add severity indicator with RED COLOR
                                if severity == 'critical':
                                    report_lines.append(f"<span style='color: #ff4444;'>❌ {description}</span>")
                                elif severity == 'high':
                                    report_lines.append(f"<span style='color: #ff4444;'>⚠️ {description}</span>")
                                else:
                                    report_lines.append(f"<span style='color: #ff4444;'>ℹ️ {description}</span>")
                                    
                                if recommendation:
                                    report_lines.append(f"<span style='color: #ff4444;'>   → {recommendation}</span>")
                            else:
                                report_lines.append(f"<span style='color: #ff4444;'>• {issue}</span>")
                    else:
                        report_lines.append("No manufacturability issues found.")
                    report_lines.append("")
                    
                    # Add cost analysis if available
                    cost_analysis = data.get('cost_analysis', {})
                    if cost_analysis:
                        report_lines.append("--- Cost Analysis ---")
                        if 'estimated_cost_per_part' in cost_analysis:
                            cost = cost_analysis['estimated_cost_per_part']
                            if isinstance(cost, dict):
                                if 'inr' in cost:
                                    report_lines.append(f"Estimated Cost: ₹{cost['inr']:.2f} per part")
                                if 'usd' in cost:
                                    report_lines.append(f"Estimated Cost (USD): ${cost['usd']:.2f} per part")
                                    report_lines.append(f"Exchange Rate: 1 USD = ₹83 (approx)")
                            else:
                                report_lines.append(f"Estimated Cost: ₹{cost:.2f} per part")
                        
                        if 'material_cost' in cost_analysis:
                            report_lines.append(f"Material Cost: ₹{cost_analysis['material_cost']:.2f}")
                        if 'processing_cost' in cost_analysis:
                            report_lines.append(f"Processing Cost: ₹{cost_analysis['processing_cost']:.2f}")
                        if 'tooling_cost' in cost_analysis:
                            report_lines.append(f"Tooling Cost: ₹{cost_analysis['tooling_cost']:.2f}")
                        report_lines.append("")
                    
                    # Add process recommendations
                    process_recs = data.get('process_recommendations', [])
                    if process_recs:
                        report_lines.append("--- Process Recommendations ---")
                        for proc in process_recs:
                            if isinstance(proc, dict):
                                process_name = proc.get('process', 'Unknown Process')
                                suitability = proc.get('suitability_score', 'N/A')
                                cost = proc.get('estimated_cost', 'N/A')
                                report_lines.append(f"• {process_name}: Suitability {suitability}/100, Cost: {cost}")
                                
                                advantages = proc.get('advantages', [])
                                if advantages:
                                    for adv in advantages:
                                        report_lines.append(f"  ✓ {adv}")
                                        
                                limitations = proc.get('limitations', [])
                                if limitations:
                                    for lim in limitations:
                                        report_lines.append(f"  ⚠ {lim}")
                            else:
                                report_lines.append(f"• {proc}")
                        report_lines.append("")
                    
                    # Add AI insights if available (from hybrid analysis)
                    ai_insights = data.get('ai_insights', {})
                    if ai_insights:
                        report_lines.append("--- AI Insights ---")
                        if ai_insights.get('ai_analysis_available'):
                            complexity = ai_insights.get('complexity_rating', 'Unknown')
                            moldability = ai_insights.get('moldability_score', 0)
                            report_lines.append(f"Complexity Rating: {complexity}")
                            report_lines.append(f"Moldability Score: {moldability}/10")
                            report_lines.append("AI Analysis: Available")
                        else:
                            report_lines.append("AI Analysis: Not Available")
                            note = ai_insights.get('note', '')
                            if note:
                                report_lines.append(f"Note: {note}")
                        report_lines.append("")
                    
                    # Add Indian market context
                    indian_context = data.get('indian_market_context', {})
                    if indian_context:
                        report_lines.append("--- Indian Market Context ---")
                        if 'suppliers' in indian_context:
                            suppliers = indian_context['suppliers']
                            if suppliers:
                                report_lines.append("Recommended Suppliers:")
                                for supplier in suppliers:
                                    if isinstance(supplier, dict):
                                        name = supplier.get('name', 'Unknown')
                                        location = supplier.get('location', 'Unknown')
                                        specialization = supplier.get('specialization', '')
                                        report_lines.append(f"  • {name} ({location}) - {specialization}")
                                    else:
                                        report_lines.append(f"  • {supplier}")
                        
                        if 'lead_times' in indian_context:
                            lead_times = indian_context['lead_times']
                            report_lines.append(f"Typical Lead Times: {lead_times}")
                        
                        if 'market_rates' in indian_context:
                            rates = indian_context['market_rates']
                            if isinstance(rates, dict):
                                for process, rate in rates.items():
                                    report_lines.append(f"Market Rate ({process}): {rate}")
                            else:
                                report_lines.append(f"Market Rates: {rates}")
                        
                        if 'quality_standards' in indian_context:
                            standards = indian_context['quality_standards']
                            report_lines.append(f"Quality Standards: {standards}")
                        report_lines.append("")
                    
                    # Add analysis summary if available (from hybrid analysis)
                    analysis_summary = data.get('analysis_summary', {})
                    if analysis_summary:
                        report_lines.append("--- Analysis Summary ---")
                        primary = analysis_summary.get('primary_analysis', '')
                        if primary:
                            report_lines.append(f"Primary Analysis: {primary}")
                        
                        ai_enhancement = analysis_summary.get('ai_enhancement', '')
                        if ai_enhancement:
                            report_lines.append(f"AI Enhancement: {ai_enhancement}")
                        
                        cost_analysis = analysis_summary.get('cost_analysis', '')
                        if cost_analysis:
                            report_lines.append(f"Cost Analysis: {cost_analysis}")
                        
                        confidence = analysis_summary.get('confidence_level', '')
                        if confidence:
                            report_lines.append(f"Confidence Level: {confidence}")
                        report_lines.append("")
                    
                    # Add alternative materials from cloud AI (if available)
                    alt_materials = data.get('alternative_materials', [])
                    if alt_materials:
                        report_lines.append("--- AI-Recommended Alternative Materials ---")
                        for material in alt_materials:
                            report_lines.append(f"• {material}")
                        report_lines.append("")
                    
                    # Add alternative processes from cloud AI (if available)
                    alt_processes = data.get('alternative_processes_ai', [])
                    if alt_processes:
                        report_lines.append("--- AI-Recommended Alternative Processes ---")
                        for process in alt_processes:
                            report_lines.append(f"• {process}")
                        report_lines.append("")
                    
                    # Add expert recommendations
                    if recommendations:
                        report_lines.append("--- Expert Recommendations ---")
                        for rec in recommendations:
                            if isinstance(rec, dict):
                                description = rec.get('description', 'Unknown recommendation')
                                priority = rec.get('priority', '')
                                if priority:
                                    report_lines.append(f"• [{priority}] {description}")
                                else:
                                    report_lines.append(f"• {description}")
                            else:
                                report_lines.append(f"• {rec}")
                    
                    report_text = "\n".join(report_lines)
                    print(f"DEBUG: Generated comprehensive report text of length {len(report_text)}")
                    
                    # Apply red color to Manufacturing Issues section for HTML display
                    report_text_with_color = report_text.replace('--- Manufacturing Issues', '--- <span style="color: #ff4444; font-weight: bold;">Manufacturing Issues')
                    report_text_with_color = report_text_with_color.replace(') ---', ') ---</span>')
                    print(f"DEBUG: Applied red color styling to Manufacturing Issues section")
                    
                    data['report_text'] = report_text_with_color
                
                # Create a formatted message
                message = f"<b>Advanced DFM Analysis Results</b><br>"
                message += f"<b>Process:</b> {process_text}<br>"
                message += f"<b>Material:</b> {material_text}<br>"
                message += f"<b>Production Volume:</b> {production_volume} units<br>"
                message += f"<b>Manufacturability Score:</b> {score}/100<br><br>"
                
                # Check if we have a pre-formatted report text
                report_text = data.get('report_text', '')
                if report_text:
                    print(f"DEBUG: Processing report_text for display, length: {len(report_text)}")
                    # Convert the report text to HTML with red color for Manufacturing Issues
                    report_html = report_text.replace('\n', '<br>')
                    # Apply red color to Manufacturing Issues section
                    report_html = report_html.replace('--- Manufacturing Issues', '<span style="color: #ff4444; font-weight: bold;">--- Manufacturing Issues')
                    report_html = report_html.replace(') ---', ') ---</span>')
                    print(f"DEBUG: HTML report length: {len(report_html)}")
                    message += f"<div style='background-color: #2d2d2d; color: #ffffff; padding: 10px; border-radius: 5px;'>{report_html}</div><br>"
                    print("DEBUG: Added report HTML to message")
                    
                    # Also print the report to the console for debugging
                    print("\n=== DFM REPORT TEXT ===\n")
                    print(report_text)
                    print("\n=== END DFM REPORT TEXT ===\n")
                else:
                    print("DEBUG: No report_text available for display")
                
                # Issues are already displayed in the report above, no need to duplicate them here
                
                # Get cost analysis if advanced analysis was enabled
                if advanced_analysis:
                    cost_analysis = self.mfg_feature_manager.get_cost_analysis()
                    if cost_analysis:
                        message += "<b>Cost Analysis:</b><br>"
                        total_cost = cost_analysis.get('total_cost', 0)
                        message += f"Total Cost: ₹{total_cost:.2f}<br>"
                        
                        # Show cost breakdown
                        breakdown = cost_analysis.get('cost_breakdown', {})
                        if breakdown:
                            message += "<u>Cost Breakdown:</u><br>"
                            for category, amount in breakdown.items():
                                message += f"- {category}: ${float(amount):.2f}<br>"
                            message += "<br>"
                    
                    # Get alternative processes
                    alt_processes = self.mfg_feature_manager.get_alternative_processes()
                    if alt_processes:
                        message += "<b>Alternative Manufacturing Processes:</b><br>"
                        for proc in alt_processes:
                            proc_name = proc.get('process_name', 'Unknown')
                            suitability = proc.get('suitability_score', 0)
                            est_cost = proc.get('estimated_cost', 0)
                            # Convert cost to INR if it's in USD
                            if isinstance(est_cost, str) and '$' in est_cost:
                                # Extract numeric value and convert
                                import re
                                usd_match = re.search(r'\$([\d.]+)', est_cost)
                                if usd_match:
                                    usd_value = float(usd_match.group(1))
                                    inr_value = usd_value * 83
                                    cost_display = f"₹{inr_value:.2f}"
                                else:
                                    cost_display = est_cost.replace('$', '₹')
                            elif isinstance(est_cost, (int, float)):
                                cost_display = f"₹{est_cost:.2f}"
                            else:
                                cost_display = str(est_cost).replace('$', '₹')
                            message += f"- {proc_name}: Suitability {suitability}/100, Est. Cost: {cost_display}<br>"
                        message += "<br>"
                
                # Display expert recommendations
                if recommendations:
                    message += "<b>Expert Recommendations:</b><br>"
                    for i, rec in enumerate(recommendations):
                        message += f"{i+1}. {rec}<br>"
                
                # Add the formatted message to chat
                print("DEBUG: Adding DFM analysis results to chat")
                self.add_assistant_message(message)
                print("DEBUG: DFM analysis results added to chat")
                
                # Don't automatically visualize - only when user clicks "Show Problem Areas" button
                print("DEBUG: Using direct visualization to bypass cloud_integration issues")
                print(f"DEBUG: Found {len(issues)} issues to visualize")
                if len(issues) > 0:
                    print(f"DEBUG: First issue: {issues[0]}")
                    for i, issue in enumerate(issues):
                        title = issue.get('title', 'Unknown issue')
                        location = issue.get('location', 'Unknown location')
                        print(f"DEBUG: Issue {i+1}: {title[:50]}... at location {location}")
                self.add_system_message("DFM analysis complete. Issues visualized in the 3D view.")
                
                # SHOW PROBLEM AREAS BUTTONS AFTER SUCCESSFUL DFM ANALYSIS (RESTORED WORKFLOW)
                print(f"DEBUG: Final button visibility check - issues length: {len(issues)}")
                print(f"DEBUG: Issues content: {issues}")
                if issues:  # Only show if there are actual issues to visualize
                    print("DEBUG: SHOWING Problem Areas button - issues found!")
                    self.show_problems_button.setVisible(True)
                    self.add_system_message("[OK] Click 'Show Problem Areas' to highlight manufacturing issues with colored overlays.")
                else:
                    print("DEBUG: NOT showing Problem Areas button - no issues found")
                    self.add_system_message("ℹ️ No manufacturing issues found - no problem areas to highlight.")
            else:
                error_msg = result.get('error', 'Unknown error during DFM analysis') if result else "Failed to get DFM analysis results"
                self.add_system_message(f"Error: {error_msg}")
                self.add_assistant_message("I couldn't complete the DFM analysis. Please check if your model is valid and try again.")
        except Exception as e:
            self.add_system_message(f"Error during DFM analysis: {str(e)}")
            traceback.print_exc()
        finally:
            # Reset status
            self.cloud_feature_status.setText("Ready")
    
    def on_cost_clicked(self):
        """Handle cost estimation button click with enhanced options"""
        self.add_system_message("Preparing cost estimation...")
        try:
            # Check if there's an active document
            if not FreeCAD.ActiveDocument:
                self.add_system_message("No active document found")
                self.add_assistant_message("Please open or create a model before running cost estimation.")
                return
            
            # Create dialog for cost estimation options
            dialog = QtWidgets.QDialog(self)
            dialog.setWindowTitle("Advanced Cost Estimation Options")
            dialog.setMinimumWidth(400)
            
            # Create form layout for options
            form_layout = QtWidgets.QFormLayout(dialog)
            
            # Manufacturing process selection
            process_combo = QtWidgets.QComboBox()
            process_combo.addItems([
                "3D Printing (FDM)", 
                "CNC Machining", 
                "Injection Molding",
                "Sheet Metal Forming",
                "Die Casting"
            ])
            form_layout.addRow("Manufacturing Process:", process_combo)
            
            # Material selection
            material_combo = QtWidgets.QComboBox()
            material_combo.addItems([
                "PLA", "ABS", "Nylon",  # 3D Printing materials
                "Aluminum", "Steel", "Brass",  # Metals
                "Polypropylene", "ABS", "Polycarbonate"  # Injection molding materials
            ])
            form_layout.addRow("Material:", material_combo)
            
            # Production volume
            volume_spin = QtWidgets.QSpinBox()
            volume_spin.setRange(1, 1000000)
            volume_spin.setValue(100)
            volume_spin.setSingleStep(10)
            form_layout.addRow("Production Volume:", volume_spin)
            
            # Region selection
            region_combo = QtWidgets.QComboBox()
            region_combo.addItems(["Global", "North America", "Europe", "Asia", "Other"])
            form_layout.addRow("Region:", region_combo)
            
            # Add buttons
            button_box = QtWidgets.QDialogButtonBox(
                QtWidgets.QDialogButtonBox.Ok | QtWidgets.QDialogButtonBox.Cancel
            )
            button_box.accepted.connect(dialog.accept)
            button_box.rejected.connect(dialog.reject)
            form_layout.addRow(button_box)
            
            # Show dialog and get results
            if dialog.exec_() != QtWidgets.QDialog.Accepted:
                self.add_system_message("Cost estimation cancelled")
                return
            
            # Get selected options
            process_text = process_combo.currentText()
            material_text = material_combo.currentText().lower()
            production_volume = volume_spin.value()
            region_text = region_combo.currentText().lower().replace(" ", "_")
            
            # Map process text to process code
            process_map = {
                "3D Printing (FDM)": "3d_printing",
                "CNC Machining": "cnc_machining",
                "Injection Molding": "injection_molding",
                "Sheet Metal Forming": "sheet_metal",
                "Die Casting": "die_casting"
            }
            process_code = process_map.get(process_text, "3d_printing")
            
            # Update status
            self.cloud_feature_status.setText("Processing cost estimation...")
            self.add_system_message(f"Running cost estimation for {process_text} with {material_text} material...")
            
            # Run cost estimation using the manufacturing feature manager with advanced options
            result = self.mfg_feature_manager.estimate_cost(
                manufacturing_process=process_code,
                material=material_text,
                quantity=production_volume,
                region=region_text
            )
            
            if result and result.get('success'):
                # Try to get enhanced cost analysis from DFM engine first
                cost_analysis = self.mfg_feature_manager.get_cost_analysis()
                
                if cost_analysis:
                    # Use the enhanced cost analysis from DFM engine
                    total_cost = cost_analysis.get('total_cost', 0)
                    currency = cost_analysis.get('currency', 'USD')
                    breakdown = cost_analysis.get('cost_breakdown', {})
                    optimization = cost_analysis.get('optimization_suggestions', [])
                else:
                    # Fall back to standard cost estimation
                    total_cost = result.get('total_cost', 0)
                    currency = result.get('currency', 'USD')
                    breakdown = result.get('cost_breakdown', {})
                    optimization = result.get('optimization_suggestions', [])
                
                # Create a formatted message
                message = f"<b>Cost Estimation Results</b><br>"
                message += f"<b>Total Estimated Cost:</b> {currency} {total_cost:.2f}<br><br>"
                
                if breakdown:
                    message += "<b>Cost Breakdown:</b><br>"
                    for category, amount in breakdown.items():
                        message += f"{category}: {currency} {float(amount):.2f}<br>"
                    message += "<br>"
                
                if optimization:
                    message += "<b>Cost Optimization Suggestions:</b><br>"
                    for i, suggestion in enumerate(optimization):
                        message += f"{i+1}. {suggestion}<br>"
                
                # Add the formatted message to chat
                self.add_assistant_message(message)
            else:
                error_msg = result.get('error', 'Unknown error during cost estimation') if result else "Failed to get cost estimation results"
                self.add_system_message(f"Error: {error_msg}")
                self.add_assistant_message("I couldn't complete the cost estimation. Please check if your model is valid and try again.")
        except Exception as e:
            self.add_system_message(f"Error during cost estimation: {str(e)}")
            traceback.print_exc()
        finally:
            # Reset status
            self.cloud_feature_status.setText("Ready")
    
    def on_tools_clicked(self):
        """Handle tool recommendations button click with enhanced options"""
        self.add_system_message("Preparing tool recommendations...")
        try:
            # Check if there's an active document
            if not FreeCAD.ActiveDocument:
                self.add_system_message("No active document found")
                self.add_assistant_message("Please open or create a model before running tool recommendations.")
                return
            
            # Create dialog for tool recommendation options
            dialog = QtWidgets.QDialog(self)
            dialog.setWindowTitle("Advanced Tool Recommendation Options")
            dialog.setMinimumWidth(400)
            
            # Create form layout for options
            form_layout = QtWidgets.QFormLayout(dialog)
            
            # Manufacturing process selection (focus on machining processes)
            process_combo = QtWidgets.QComboBox()
            process_combo.addItems([
                "CNC Machining", 
                "Milling",
                "Turning",
                "Drilling",
                "EDM"
            ])
            form_layout.addRow("Manufacturing Process:", process_combo)
            
            # Material selection
            material_combo = QtWidgets.QComboBox()
            material_combo.addItems([
                "Aluminum", "Steel", "Stainless Steel", "Brass", "Titanium", 
                "Plastic", "Composite", "Wood"
            ])
            form_layout.addRow("Material:", material_combo)
            
            # Machine type selection
            machine_combo = QtWidgets.QComboBox()
            machine_combo.addItems([
                "3-Axis CNC", "5-Axis CNC", "CNC Lathe", "CNC Mill", "Universal"
            ])
            form_layout.addRow("Machine Type:", machine_combo)
            
            # Add buttons
            button_box = QtWidgets.QDialogButtonBox(
                QtWidgets.QDialogButtonBox.Ok | QtWidgets.QDialogButtonBox.Cancel
            )
            button_box.accepted.connect(dialog.accept)
            button_box.rejected.connect(dialog.reject)
            form_layout.addRow(button_box)
            
            # Show dialog and get results
            if dialog.exec_() != QtWidgets.QDialog.Accepted:
                self.add_system_message("Tool recommendations cancelled")
                return
            
            # Get selected options
            process_text = process_combo.currentText()
            material_text = material_combo.currentText().lower()
            machine_type = machine_combo.currentText().lower().replace("-", "_").replace(" ", "_")
            
            # Map process text to process code
            process_map = {
                "CNC Machining": "cnc_machining",
                "Milling": "milling",
                "Turning": "turning",
                "Drilling": "drilling",
                "EDM": "edm"
            }
            process_code = process_map.get(process_text, "cnc_machining")
            
            # Update status
            self.cloud_feature_status.setText("Processing tool recommendations...")
            self.add_system_message(f"Running tool recommendations for {process_text} with {material_text} material...")
            
            # Run tool recommendations using the manufacturing feature manager with advanced options
            result = self.mfg_feature_manager.recommend_tools(
                manufacturing_process=process_code,
                material=material_text,
                machine_type=machine_type
            )
            
            if result and result.get('success'):
                # Get data from the result
                data = result.get('data', {})
                tools = data.get('tools', [])
                machine_type_result = data.get('machine_type', machine_type)
                material_result = data.get('material', material_text)
                
                # Create a formatted message
                message = f"<b>Advanced Tool Recommendations</b><br>"
                message += f"<b>Process:</b> {process_text}<br>"
                message += f"<b>Machine Type:</b> {machine_type_result}<br>"
                message += f"<b>Material:</b> {material_result}<br><br>"
                
                if tools:
                    message += "<b>Recommended Tools:</b><br>"
                    for i, tool in enumerate(tools):
                        tool_name = tool.get('name', f"Tool {i+1}")
                        tool_type = tool.get('type', 'Unknown')
                        diameter = tool.get('diameter', 0)
                        speed = tool.get('speed', 0)
                        feed = tool.get('feed', 0)
                        
                        message += f"<b>{i+1}. {tool_name}</b> ({tool_type})<br>"
                        message += f"   Diameter: {diameter}mm | Speed: {speed} RPM | Feed: {feed} mm/min<br>"
                        
                        # Add efficiency rating if available
                        if 'efficiency_rating' in tool:
                            efficiency = tool.get('efficiency_rating', 0)
                            message += f"   Efficiency Rating: {efficiency}/100<br>"
                        
                        # Add tool path strategy if available
                        if 'recommended_strategy' in tool:
                            strategy = tool.get('recommended_strategy', '')
                            message += f"   Recommended Strategy: {strategy}<br>"
                        
                        if 'description' in tool:
                            message += f"   <i>{tool['description']}</i><br>"
                        message += "<br>"
                else:
                    message += "<b>No tool recommendations available for this model.</b><br>"
                
                # Add the formatted message to chat
                self.add_assistant_message(message)
                
                # Visualize tool paths if available
                if hasattr(self.mfg_feature_manager, 'visualize_tool_paths'):
                    self.mfg_feature_manager.visualize_tool_paths()
                    self.add_system_message("Tool paths visualized in the 3D view.")
            else:
                error_msg = result.get('error', 'Unknown error during tool recommendations') if result else "Failed to get tool recommendations"
                self.add_system_message(f"Error: {error_msg}")
                self.add_assistant_message("I couldn't get tool recommendations. Please check if your model is valid and try again.")
        except Exception as e:
            self.add_system_message(f"Error during tool recommendations: {str(e)}")
            traceback.print_exc()
        finally:
            # Reset status
            self.cloud_feature_status.setText("Ready")
    
    def on_compare_clicked(self):
        """Handle manufacturing method comparison button click"""
        self.add_system_message("Comparing manufacturing methods...")
        try:
            # Check if there's an active document
            if not FreeCAD.ActiveDocument:
                self.add_system_message("No active document found")
                self.add_assistant_message("Please open or create a model before comparing manufacturing methods.")
                return
                
            # Update status
            self.cloud_feature_status.setText("Comparing manufacturing methods...")
            
            # Compare manufacturing methods using the manufacturing feature manager
            result = self.mfg_feature_manager.compare_manufacturing_methods()
            
            if result and result.get('success'):
                # Format the comparison results for display
                comparisons = result.get('comparisons', [])
                recommendation = result.get('recommended_method', {})
                
                # Create a formatted message
                message = f"<b>Manufacturing Method Comparison</b><br><br>"
                
                if recommendation:
                    method_name = recommendation.get('name', 'Unknown')
                    reason = recommendation.get('reason', 'No specific reason provided')
                    message += f"<b>Recommended Method:</b> {method_name}<br>"
                    message += f"<b>Reason:</b> {reason}<br><br>"
                
                if comparisons:
                    message += "<b>Method Comparison:</b><br>"
                    message += "<table border='1' cellpadding='3' style='border-collapse: collapse;'>"
                    message += "<tr><th>Method</th><th>Cost</th><th>Time</th><th>Quality</th><th>Suitability</th></tr>"
                    
                    for comp in comparisons:
                        method = comp.get('method', 'Unknown')
                        cost = comp.get('cost', 'N/A')
                        time = comp.get('time', 'N/A')
                        quality = comp.get('quality', 'N/A')
                        suitability = comp.get('suitability', 0)
                        
                        # Convert suitability to stars
                        stars = '★' * int(suitability) + '☆' * (5 - int(suitability))
                        
                        message += f"<tr><td>{method}</td><td>{cost}</td><td>{time}</td><td>{quality}</td><td>{stars}</td></tr>"
                    
                    message += "</table>"
                
                # Add the formatted message to chat
                self.add_assistant_message(message)
            else:
                error_msg = result.get('error', 'Unknown error comparing manufacturing methods') if result else "Failed to compare manufacturing methods"
                self.add_system_message(f"Error: {error_msg}")
                self.add_assistant_message("I couldn't compare manufacturing methods. Please check if your model is valid and try again.")
        except Exception as e:
            self.add_system_message(f"Error comparing manufacturing methods: {str(e)}")
            traceback.print_exc()
        finally:
            # Reset status
            self.cloud_feature_status.setText("Ready")

    def on_show_problems_clicked(self):
        """Handle Show Problem Areas button click (RESTORED HEATMAP OVERLAY FEATURE)"""
        self.add_system_message("Showing manufacturing problem areas...")
        try:
            # Check if there's an active document
            if not FreeCAD.ActiveDocument:
                self.add_system_message("No active document found")
                self.add_assistant_message("Please open or create a model before showing problem areas.")
                return
                
            # Update status
            self.cloud_feature_status.setText("Visualizing problem areas...")
            
            # Get the current Claude-detected issues from the latest analysis
            current_issues = []
            if hasattr(self, 'last_analysis') and self.last_analysis:
                current_issues = self.last_analysis.get('manufacturing_issues', [])
                print(f"DEBUG: Found {len(current_issues)} current Claude issues to visualize")
                if current_issues:
                    # Handle different issue formats robustly
                    first_issue = current_issues[0]
                    issue_title = first_issue.get('title', first_issue.get('description', 'Unknown issue'))
                    print(f"DEBUG: First current issue: {issue_title}")
            
            # Pass the current issues to the visualization function
            if current_issues:
                # Update BOTH the mfg_feature_manager AND cloud_integration with current data
                current_data = {
                    "success": True,
                    "data": {
                        "manufacturing_issues": current_issues
                    }
                }
                
                # Update mfg_feature_manager
                if not hasattr(self.mfg_feature_manager, 'last_dfm_result'):
                    self.mfg_feature_manager.last_dfm_result = {}
                self.mfg_feature_manager.last_dfm_result = current_data
                
                # Update cloud_integration (this is what's actually being called)
                if hasattr(self, 'cloud_integration') and self.cloud_integration:
                    if not hasattr(self.cloud_integration, 'last_dfm_result'):
                        self.cloud_integration.last_dfm_result = {}
                    self.cloud_integration.last_dfm_result = current_data
                    print(f"DEBUG: Updated cloud_integration with {len(current_issues)} current issues")
                
                print(f"DEBUG: Updated both managers with {len(current_issues)} current issues")
            
            # Use the existing visualize_dfm_issues function
            success = self.mfg_feature_manager.visualize_dfm_issues()
            
            if success:
                self.add_system_message("[OK] Problem areas visualized with colored overlays")
                self.add_assistant_message(
                    "<b>Manufacturing Problem Areas Displayed</b><br><br>"
                    "I've overlaid transparent colored markers on your CAD model to highlight manufacturing issues:<br><br>"
                    "🔴 <b>Red:</b> Critical/High severity issues<br>"
                    "🟠 <b>Orange:</b> Medium severity issues<br>"
                    "🔵 <b>Blue:</b> Low severity issues<br><br>"
                    "Each marker shows the location and description of manufacturing problems. "
                    "Click 'Hide Problem Areas' to remove the overlays."
                )
                
                # Show Hide button and hide Show button (CORRECT WORKFLOW)
                self.show_problems_button.setVisible(False)
                self.hide_problems_button.setVisible(True)
            else:
                self.add_system_message("No manufacturing issues found to visualize")
                self.add_assistant_message("No manufacturing problem areas were detected in your current model.")
        except Exception as e:
            self.add_system_message(f"Error showing problem areas: {str(e)}")
            traceback.print_exc()
        finally:
            # Reset status
            self.cloud_feature_status.setText("Ready")
    
    def on_hide_problems_clicked(self):
        """Handle Hide Problem Areas button click (ROBUST DFM VISUALIZATION SYSTEM)"""
        self.add_system_message("Hiding manufacturing problem areas...")
        try:
            # Check if there's an active document
            if not FreeCAD.ActiveDocument:
                self.add_system_message("No active document found")
                return
                
            # Update status
            self.cloud_feature_status.setText("Removing problem area overlays...")
            
            # Use the robust DFM visualization system to hide overlays
            doc = FreeCAD.ActiveDocument
            hidden_count = 0
            
            # Find all objects with DFM overlays and hide them
            for obj in doc.Objects:
                if hasattr(obj, 'Mesh') or hasattr(obj, 'Shape'):
                    try:
                        # Try to toggle overlays for this object (hide them)
                        self.mfg_feature_manager.toggle_overlays(obj.Name, visible=False)
                        hidden_count += 1
                        print(f"DEBUG: Hidden overlays for {obj.Name}")
                    except Exception as toggle_error:
                        print(f"DEBUG: No overlays found for {obj.Name}: {toggle_error}")
                        continue
            
            # Also remove any remaining old-style DFM visualization
            self.mfg_feature_manager._remove_existing_dfm_visualization(doc)
            
            if hidden_count > 0:
                self.add_system_message(f"[OK] Problem area overlays hidden for {hidden_count} objects")
                self.add_assistant_message(
                    "<b>Problem Area Overlays Hidden</b><br><br>"
                    f"Manufacturing problem area overlays have been hidden for {hidden_count} objects. "
                    "The overlays are still available and can be shown again using 'Show Problem Areas'."
                )
            else:
                self.add_system_message("[OK] No active overlays found to hide")
                self.add_assistant_message(
                    "<b>No Active Overlays</b><br><br>"
                    "No manufacturing problem area overlays were found to hide. "
                    "Use 'Show Problem Areas' to create overlays first."
                )
            
            # Hide both buttons - workflow complete (CORRECT WORKFLOW)
            self.show_problems_button.setVisible(False)
            self.hide_problems_button.setVisible(False)
        except Exception as e:
            self.add_system_message(f"Error hiding problem areas: {str(e)}")
            traceback.print_exc()
        finally:
            # Reset status
            self.cloud_feature_status.setText("Ready")

    
    def closeEvent(self, event):
        """Handle window close event"""
        global _STANDALONE_INSTANCE
        print("Closing Standalone Co-Pilot")
        _STANDALONE_INSTANCE = None
        event.accept()

class StandaloneCoPilotTaskPanel:
    """Task panel for the Standalone Co-Pilot"""
    
    def __init__(self, widget):
        """Initialize the task panel"""
        self.form = widget
        self.widget = widget
        print("StandaloneCoPilotTaskPanel initialized")
    
    def accept(self):
        """Handle accept event"""
        print("StandaloneCoPilotTaskPanel accepted")
        self._cleanup()
        return True
    
    def reject(self):
        """Handle reject event"""
        print("StandaloneCoPilotTaskPanel rejected")
        self._cleanup()
        return True
    
    def _cleanup(self):
        """Clean up resources"""
        global _STANDALONE_INSTANCE
        _STANDALONE_INSTANCE = None
        print("Reset _STANDALONE_INSTANCE to None")
    
    def getStandardButtons(self):
        """Return standard buttons"""
        return 0

def show_standalone_copilot():
    """Show the standalone co-pilot with singleton pattern"""
    global _STANDALONE_INSTANCE
    
    print("\n=== STARTING STANDALONE CO-PILOT ===\n")
    
    # Check if an instance already exists
    if _STANDALONE_INSTANCE is not None:
        print("Standalone Co-Pilot is already running - activating existing instance")
        try:
            # Try to bring existing instance to front
            _STANDALONE_INSTANCE.activateWindow()
            _STANDALONE_INSTANCE.raise_()
            
            # Show message to user
            QtWidgets.QMessageBox.information(
                None,
                "Co-Pilot Already Running",
                "Manufacturing Co-Pilot is already running. Using the existing instance."
            )
        except Exception as e:
            print(f"Error activating existing instance: {e}")
        return
    
    try:
        # Close any active FreeCAD task dialogs
        if FreeCADGui.Control.activeDialog():
            print("Closing active FreeCAD task dialog")
            FreeCADGui.Control.closeDialog()
        
        # Create new instance
        copilot = StandaloneCoPilot()
        _STANDALONE_INSTANCE = copilot
        
        # Show in FreeCAD task panel
        panel = StandaloneCoPilotTaskPanel(copilot)
        FreeCADGui.Control.showDialog(panel)
        print("Standalone Co-Pilot shown in task panel")
        
        print("\n=== STANDALONE CO-PILOT STARTED SUCCESSFULLY ===\n")
    except Exception as e:
        print(f"Error showing Standalone Co-Pilot: {e}")
        traceback.print_exc()
        _STANDALONE_INSTANCE = None
        
        # Show error message
        QtWidgets.QMessageBox.critical(
            None,
            "Co-Pilot Error",
            f"Failed to start Standalone Co-Pilot:\n\n{str(e)}"
        )

# Main entry point
if __name__ == "__main__":
    print("\n=== STANDALONE CO-PILOT MACRO STARTING ===\n")
    
    try:
        # Show the standalone co-pilot
        show_standalone_copilot()
    except Exception as e:
        print(f"ERROR starting Standalone Co-Pilot: {e}")
        traceback.print_exc()
        
        # Show error message
        try:
            QtWidgets.QMessageBox.critical(
                None,
                "Co-Pilot Error",
                f"Failed to start Standalone Co-Pilot:\n\n{str(e)}"
            )
        except Exception as msg_err:
            print(f"Error showing message: {msg_err}")
    
    print("\n=== STANDALONE CO-PILOT MACRO INITIALIZATION COMPLETE ===\n")
