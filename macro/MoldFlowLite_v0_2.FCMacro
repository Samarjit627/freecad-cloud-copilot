def add_colorbar_legend(bbox, COLORS):
    try:
        # Place a vertical stack of small boxes to the +X side of the model bbox
        dx = max(1.0, 0.02*bbox.DiagonalLength)
        lx = max(1.0, 0.03*bbox.XLength)
        ly = max(1.0, 0.03*bbox.YLength)
        lz = max(1.0, 0.80*ly)
        base_x = bbox.XMax + dx
        base_y = (bbox.YMin + bbox.YMax)*0.5 - 0.5*lz
        base_z = bbox.ZMin + 0.02*bbox.ZLength
        step = lz/len(COLORS)
        for i, col in enumerate(COLORS):
            obj = DOC.addObject('Part::Box', f"{OVERLAY_TAG}LEGEND_{i}")
            obj.Length = lx
            obj.Width = ly*0.25
            obj.Height = step
            obj.Placement = FreeCAD.Placement(FreeCAD.Vector(base_x, base_y + i*step, base_z), FreeCAD.Rotation())
            obj.ViewObject.ShapeColor = col
            obj.ViewObject.Transparency = 0
        try:
            DOC.recompute()
        except Exception:
            pass
    except Exception:
        pass
# -*- coding: utf-8 -*-
# MoldFlow-Lite v0.2 — FreeCAD macro (reconstructed)
# - Dot heatmap overlay with color legend
# - Weld-line toggle
# - Status summary and suggestions
# - Global placement alignment, seed snapping, UI responsiveness

import os, json, math, heapq, time, random
from collections import deque
import FreeCAD as App
import FreeCADGui as Gui
import Part

try:
    from PySide2 import QtWidgets, QtCore
except ImportError:
    from PySide import QtGui as QtWidgets
    from PySide import QtCore

DOC = App.ActiveDocument
VW = Gui.ActiveDocument.ActiveView if Gui.ActiveDocument else None
OVERLAY_TAG = "_MFLITE_OVERLAY_"
WELD_OBJ_NAME = f"{OVERLAY_TAG}WELD"
HEUR_DIR = os.path.join(App.getUserAppDataDir(), "MoldFlowLite")
HEUR_PATH = os.path.join(HEUR_DIR, "heuristics.json")

def process_events():
    try:
        QtWidgets.QApplication.processEvents(QtCore.QEventLoop.AllEvents, 25)
    except Exception:
        pass

# Materials
MATERIALS = {
    "ABS (general purpose)": {"viscosity_index": 1.0, "melt_temp": 240, "mold_temp": 70, "min_wall": 1.2, "k": 0.18, "rho": 1040, "cp": 1300, "vent_depth_mm": 0.02, "notes": "Balanced flow. Knit lines visible on glossy surfaces."},
    "PP (MFI~20)": {"viscosity_index": 0.8, "melt_temp": 220, "mold_temp": 40, "min_wall": 1.0, "k": 0.22, "rho": 905, "cp": 1900, "vent_depth_mm": 0.03, "notes": "Flows easily; warpage risk if asymmetry."},
    "PC": {"viscosity_index": 1.3, "melt_temp": 290, "mold_temp": 95, "min_wall": 1.5, "k": 0.20, "rho": 1200, "cp": 1200, "vent_depth_mm": 0.02, "notes": "Needs higher mold temp for knit strength."},
    "Nylon (PA6)": {"viscosity_index": 1.1, "melt_temp": 255, "mold_temp": 70, "min_wall": 1.2, "k": 0.25, "rho": 1140, "cp": 1700, "vent_depth_mm": 0.03, "notes": "Moisture-sensitive; vents important."}
}

DEFAULT_HEUR = {"version": "0.2","scrap_weights": {"time": 0.45, "thin": 0.35, "trap": 0.20},"thin_cap_pct": 15.0,"trap_norm_count": 12.0,"weld_dt_threshold": 0.12,"weld_stride": 2,"gate_candidates_per_face": 12,"max_weld_segments": 2000,"cycle": {"K_cool": 0.55, "inj_seconds_base": 0.6, "pack_seconds": 0.8},"rib_rules": {"ratio_to_wall": [0.5, 0.6], "base_fillet_mm": 0.25},"vent_depth_by_material_default_mm": 0.02}

def ensure_heuristics():
    os.makedirs(HEUR_DIR, exist_ok=True)
    if not os.path.exists(HEUR_PATH):
        with open(HEUR_PATH, "w") as f: json.dump(DEFAULT_HEUR, f, indent=2)
    with open(HEUR_PATH, "r") as f: heur = json.load(f)
    for k,v in DEFAULT_HEUR.items():
        if k not in heur: heur[k]=v
    with open(HEUR_PATH, "w") as f: json.dump(heur, f, indent=2)
    return heur

# Overlay helpers
def clear_overlay():
    if not DOC: return
    for obj in list(DOC.Objects):
        if obj.Name.startswith(OVERLAY_TAG):
            DOC.removeObject(obj.Name)
    try:
        DOC.recompute()
    except Exception:
        pass

def add_compound_shape(shapes, name, color=(0.8,0.2,0.2), alpha=70):
    if not shapes: return None
    comp = Part.Compound(shapes) if len(shapes)>1 else shapes[0]
    obj = DOC.addObject("Part::Feature", name)
    obj.Shape = comp
    obj.ViewObject.ShapeColor = color
    obj.ViewObject.Transparency = alpha
    obj.ViewObject.DisplayMode = "Shaded"
    try: DOC.recompute()
    except Exception: pass
    return obj


# ----- Markers and dots -----
def add_marker(pt, kind="gate"):
    r = 1.5
    if kind=="gate": color=(0.1,0.8,0.3); r=2.0
    elif kind=="trap": color=(0.2,0.5,0.9); r=1.6
    else: color=(0.8,0.2,0.2)
    sph = Part.makeSphere(r, App.Vector(*pt))
    return add_compound_shape([sph], f"{OVERLAY_TAG}{kind.upper()}", color=color, alpha=30)

def add_colored_spheres(points, radius=1.0, color_rgb=(1,0,0), alpha=70, label_suffix=""):
    spheres=[Part.makeSphere(radius, App.Vector(x,y,z)) for (x,y,z) in points]
    return add_compound_shape(spheres, f"{OVERLAY_TAG}DOTS{label_suffix}", color=color_rgb, alpha=alpha)


# ---------------- Geometry helpers ----------------
def get_selected_solid_and_faces():
    sel = Gui.Selection.getSelectionEx()
    solid=None; faces=[]
    if sel:
        for s in sel:
            if hasattr(s.Object, "Shape") and s.Object.Shape:
                sh = s.Object.Shape.copy()
                try:
                    sh.Placement = s.Object.getGlobalPlacement()
                except Exception:
                    pass
                if sh.Solids and not solid:
                    solid = sh.Solids[0]
                for sub in s.SubObjects:
                    if isinstance(sub, Part.Face):
                        f=sub.copy()
                        try:
                            f.transformShape(s.Object.getGlobalPlacement().toMatrix(), True)
                        except Exception:
                            pass
                        faces.append(f)
    if not solid and DOC:
        for obj in DOC.Objects:
            try:
                if hasattr(obj, "Shape") and obj.Shape and obj.Shape.Solids:
                    sh = obj.Shape.copy()
                    try: sh.Placement = obj.getGlobalPlacement()
                    except Exception: pass
                    solid = sh.Solids[0]; break
            except Exception:
                continue
    if not solid:
        raise RuntimeError("No solid found. Select a solid body or ensure the document contains a watertight solid.")
    return solid, faces

def preflight_dims(solid, res=64, pad=0.5):
    bb=solid.BoundBox
    sx,sy,sz = bb.XLength, bb.YLength, bb.ZLength
    L=max(sx,sy,sz)
    h=L/max(8,res)
    nx=int((sx+2*pad*h)/h); ny=int((sy+2*pad*h)/h); nz=int((sz+2*pad*h)/h)
    return (nx,ny,nz), round(h,3), nx*ny*nz

def voxelize_solid(solid, res=64, pad=0.5):
    bb=solid.BoundBox
    sx,sy,sz = bb.XLength, bb.YLength, bb.ZLength
    L=max(sx,sy,sz)
    h = L/float(res)
    origin=(bb.XMin-pad*h, bb.YMin-pad*h, bb.ZMin-pad*h)
    nx=int((sx+2*pad*h)/h)+1; ny=int((sy+2*pad*h)/h)+1; nz=int((sz+2*pad*h)/h)+1
    inside=[[[False]*nz for _ in range(ny)] for __ in range(nx)]
    tol=max(0.05*h, 0.05)
    for i in range(nx):
        x=origin[0]+(i+0.5)*h
        for j in range(ny):
            y=origin[1]+(j+0.5)*h
            for k in range(nz):
                z=origin[2]+(k+0.5)*h
                try:
                    inside[i][j][k]=solid.isInside(App.Vector(x,y,z), tol, True)
                except Exception:
                    inside[i][j][k]=False
        if (i%4)==0: process_events()
    return origin, h, (nx,ny,nz), inside

def dist_transform(inside):
    nx,ny,nz=len(inside),len(inside[0]),len(inside[0][0])
    INF=10**9
    D=[[[INF]*nz for _ in range(ny)] for __ in range(nx)]
    dq=deque()
    for i in range(nx):
        for j in range(ny):
            for k in range(nz):
                if not inside[i][j][k]:
                    D[i][j][k]=0; dq.append((i,j,k))
    def nb(i,j,k):
        for di,dj,dk in ((1,0,0),(-1,0,0),(0,1,0),(0,-1,0),(0,0,1),(0,0,-1)):
            ii, jj, kk = i+di, j+dj, k+dk
            if 0<=ii<nx and 0<=jj<ny and 0<=kk<nz:
                yield ii,jj,kk
    while dq:
        i,j,k=dq.popleft(); d=D[i][j][k]
        for ii,jj,kk in nb(i,j,k):
            nd=d+1
            if D[ii][jj][kk]>nd:
                D[ii][jj][kk]=nd; dq.append((ii,jj,kk))
    return D

def idx_from_point(p, origin, h, dims):
    i=int((p[0]-origin[0])//h); j=int((p[1]-origin[1])//h); k=int((p[2]-origin[2])//h)
    i=max(0,min(dims[0]-1,i)); j=max(0,min(dims[1]-1,j)); k=max(0,min(dims[2]-1,k))
    return i,j,k

def nearest_inside(idx, inside, max_r=4):
    i,j,k=idx; nx,ny,nz=len(inside),len(inside[0]),len(inside[0][0])
    if inside[i][j][k]: return idx
    for r in range(1,max_r+1):
        for ii in range(max(0,i-r),min(nx-1,i+r)+1):
            for jj in range(max(0,j-r),min(ny-1,j+r)+1):
                for kk in range(max(0,k-r),min(nz-1,k+r)+1):
                    if inside[ii][jj][kk]: return (ii,jj,kk)
    return idx

def fast_march(inside, speed, seeds):
    nx,ny,nz=len(inside),len(inside[0]),len(inside[0][0])
    INF=1e18
    T=[[[INF]*nz for _ in range(ny)] for __ in range(nx)]
    SRC=[[[-1]*nz for _ in range(ny)] for __ in range(nx)]
    hq=[]
    for sid,(i,j,k) in enumerate(seeds):
        if inside[i][j][k]:
            T[i][j][k]=0.0; SRC[i][j][k]=sid; heapq.heappush(hq,(0.0,i,j,k))
    def nb(i,j,k):
        for di,dj,dk in ((1,0,0),(-1,0,0),(0,1,0),(0,-1,0),(0,0,1),(0,0,-1)):
            ii, jj, kk = i+di, j+dj, k+dk
            if 0<=ii<nx and 0<=jj<ny and 0<=kk<nz:
                yield ii,jj,kk
    while hq:
        t,i,j,k=heapq.heappop(hq)
        if t!=T[i][j][k]: continue
        for ii,jj,kk in nb(i,j,k):
            if not inside[ii][jj][kk]: continue
            v=speed[ii][jj][kk]
            if v<=1e-9: continue
            nt=t+1.0/v
            if nt<T[ii][jj][kk]:
                T[ii][jj][kk]=nt; SRC[ii][jj][kk]=SRC[i][j][k]
                heapq.heappush(hq,(nt,ii,jj,kk))
    return T,SRC

def render_heatmap(T, inside, origin, h, stride, COLORS, radius_scale=1.0):
    nx,ny,nz=len(inside),len(inside[0]),len(inside[0][0])
    times=[T[i][j][k] for i in range(nx) for j in range(ny) for k in range(nz) if inside[i][j][k] and T[i][j][k]<1e17]
    if not times: return (0.0,1.0),0.0,1.0
    tmin,tmax=min(times),max(times); span=max(1e-9,tmax-tmin)
    buckets=[[] for _ in range(10)]
    for i in range(0,nx,stride):
        for j in range(0,ny,stride):
            for k in range(0,nz,stride):
                if not inside[i][j][k]: continue
                tij=T[i][j][k]
                if tij>1e16: continue
                nrm=(tij-tmin)/span; b=min(9,int(nrm*9.999))
                x=origin[0]+(i+0.5)*h; y=origin[1]+(j+0.5)*h; z=origin[2]+(k+0.5)*h
                buckets[b].append((x,y,z))
    for bi,pts in enumerate(buckets):
        if pts:
            add_colored_spheres(pts, radius=radius_scale*max(0.15,0.35*h), color_rgb=COLORS[bi], alpha=70, label_suffix=f"_{bi}")
    return (tmin,tmax), tmin, span

def extract_weld_lines(T,SRC,inside,origin,h,dt_norm_thresh=0.12,stride=2,max_segments=2000):
    nx,ny,nz=len(inside),len(inside[0]),len(inside[0][0])
    times=[T[i][j][k] for i in range(nx) for j in range(ny) for k in range(nz) if inside[i][j][k] and T[i][j][k]<1e17]
    if not times: return []
    tmin,tmax=min(times),max(times); span=max(1e-9,tmax-tmin)
    segs=[]
    for i in range(0,nx,stride):
        for j in range(0,ny,stride):
            for k in range(0,nz,stride):
                if not inside[i][j][k]: continue
                for di,dj,dk in ((1,0,0),(0,1,0),(0,0,1)):
                    ii,jj,kk=i+di,j+dj,k+dk
                    if ii>=nx or jj>=ny or kk>=nz: continue
                    if not inside[ii][jj][kk]: continue
                    if SRC[i][j][k]!=SRC[ii][jj][kk]:
                        dt=abs(T[i][j][k]-T[ii][jj][kk])/span
                        if dt<=dt_norm_thresh:
                            p1=App.Vector(origin[0]+(i+0.5)*h, origin[1]+(j+0.5)*h, origin[2]+(k+0.5)*h)
                            p2=App.Vector(origin[0]+(ii+0.5)*h, origin[1]+(jj+0.5)*h, origin[2]+(kk+0.5)*h)
                            segs.append(Part.makeLine(p1,p2))
                            if len(segs)>=max_segments: return segs
    return segs

def add_colorbar_legend(bbox, COLORS):
    try:
        dx = max(1.0, 0.02*bbox.DiagonalLength)
        lx = max(1.0, 0.03*bbox.XLength)
        ly = max(1.0, 0.03*bbox.YLength)
        lz = max(1.0, 0.80*ly)
        base_x = bbox.XMax + dx
        base_y = (bbox.YMin + bbox.YMax)*0.5 - 0.5*lz
        base_z = bbox.ZMin + 0.02*bbox.ZLength
        step = lz/10.0
        COLORS=list(COLORS)
        for i, col in enumerate(COLORS):
            obj = DOC.addObject('Part::Box', f"{OVERLAY_TAG}LEGEND_{i}")
            obj.Length = lx; obj.Width = ly*0.25; obj.Height = step
            obj.Placement = App.Placement(App.Vector(base_x, base_y + i*step, base_z), App.Rotation())
            obj.ViewObject.ShapeColor = col; obj.ViewObject.Transparency = 0
        DOC.recompute()
    except Exception:
        pass


# ---------------- UI Panel ----------------
class MoldFlowLitePanel(QtWidgets.QWidget):
    def __init__(self):
        super().__init__()
        self.setWindowTitle("MoldFlow-Lite v0.2")
        self._last_maps=None; self._last_weld_segs=[]; self._last_weld_obj=None
        self._last_report=None; self._last_gate_points=[]
        self._base_faded=[]

        v=QtWidgets.QVBoxLayout(self)
        form=QtWidgets.QFormLayout()
        self.cmbMat=QtWidgets.QComboBox(); [self.cmbMat.addItem(k) for k in MATERIALS.keys()]
        self.spRes=QtWidgets.QSpinBox(); self.spRes.setRange(24,120); self.spRes.setValue(64)
        self.density=QtWidgets.QDoubleSpinBox(); self.density.setDecimals(2); self.density.setRange(0.1,1.0); self.density.setValue(0.6)
        self.thin=QtWidgets.QDoubleSpinBox(); self.thin.setDecimals(2); self.thin.setRange(0.4,3.0); self.thin.setValue(MATERIALS[self.cmbMat.currentText()]["min_wall"])
        self.cmbMat.currentIndexChanged.connect(lambda: self.thin.setValue(MATERIALS[self.cmbMat.currentText()]["min_wall"]))
        self.sz=QtWidgets.QDoubleSpinBox(); self.sz.setDecimals(2); self.sz.setRange(0.5,2.5); self.sz.setValue(1.2)
        form.addRow("Material", self.cmbMat)
        form.addRow("Grid resolution", self.spRes)
        form.addRow("Point density", self.density)
        form.addRow("Thin-wall min (mm)", self.thin)
        form.addRow("Marker size", self.sz)
        v.addLayout(form)

        self.btnFlow=QtWidgets.QPushButton("Show Mold Flow")
        self.chkFast=QtWidgets.QCheckBox("Fast preview (lower res)")
        self.btnWeld=QtWidgets.QPushButton("Toggle Weld Lines")
        self.btnClear=QtWidgets.QPushButton("Clear Overlay")
        self.btnExport=QtWidgets.QPushButton("Export JSON for GPT")
        for b in (self.btnFlow,self.chkFast,self.btnWeld,self.btnClear,self.btnExport): v.addWidget(b)
        self.out=QtWidgets.QTextEdit(); self.out.setReadOnly(True); self.out.setMinimumHeight(190); v.addWidget(self.out)

        self.btnFlow.clicked.connect(self.on_show_flow)
        self.btnWeld.clicked.connect(self.toggle_weld)
        self.btnClear.clicked.connect(self.on_clear)
        self.btnExport.clicked.connect(self.export_json)

    def _fade_scene(self, on=True):
        try:
            if on and not self._base_faded:
                for o in DOC.Objects:
                    if not o.Name.startswith(OVERLAY_TAG) and hasattr(o, 'ViewObject'):
                        self._base_faded.append((o, o.ViewObject.Transparency))
                        o.ViewObject.Transparency = min(85, o.ViewObject.Transparency+60)
            if not on and self._base_faded:
                for o, t in self._base_faded:
                    try: o.ViewObject.Transparency = t
                    except Exception: pass
                self._base_faded=[]
        except Exception:
            pass

    def on_clear(self):
        clear_overlay(); self._fade_scene(False); self.out.setPlainText("")

    def on_show_flow(self):
        try:
            clear_overlay(); self._fade_scene(True)
            mat=self.cmbMat.currentText(); res=int(self.spRes.value()); thin=float(self.thin.value()); dens=float(self.density.value())
            if self.chkFast.isChecked(): res=min(res,36)
            solid, faces = get_selected_solid_and_faces()
            gates=[]
            if faces:
                for f in faces:
                    uv=f.ParameterRange; u=(uv[0]+uv[1])*0.5; v=(uv[2]+uv[3])*0.5
                    p=f.valueAt(u,v); gates.append((p.x,p.y,p.z))
            else:
                c=solid.BoundBox.Center; gates=[(c.x,c.y,c.z)]

            # voxelize
            (dims_est, h_est, vox_est)=preflight_dims(solid, res=res, pad=0.5)
            self.out.setPlainText(f"Voxelizing… target grid {dims_est} (~{vox_est:,})")
            origin,h,dims,inside=voxelize_solid(solid, res=res, pad=0.5)
            nx,ny,nz=dims
            # maps
            D=dist_transform(inside)
            visc=MATERIALS[mat]["viscosity_index"]
            speed=[[[0.0]*nz for _ in range(ny)] for __ in range(nx)]
            thin_mask=[[[False]*nz for _ in range(ny)] for __ in range(nx)]
            for i in range(nx):
                for j in range(ny):
                    for k in range(nz):
                        if not inside[i][j][k]: continue
                        local_t_mm=2.0*D[i][j][k]*h
                        thin_mask[i][j][k]=(local_t_mm<thin)
                        speed[i][j][k]=max(1e-6,(local_t_mm/max(0.1,visc))**0.8)
                if (i%4)==0: process_events()
            seeds=[nearest_inside(idx_from_point(p,origin,h,dims), inside) for p in gates]
            T,SRC=fast_march(inside, speed, seeds)

            # render
            stride=max(1,int(round(1.0/max(0.05,dens))))
            COLORS=[(0.10,0.20,0.90),(0.05,0.50,0.95),(0.00,0.75,0.85),(0.00,0.80,0.55),(0.00,0.75,0.30),(0.35,0.75,0.10),(0.70,0.70,0.10),(0.85,0.55,0.05),(0.90,0.35,0.05),(0.90,0.10,0.10)]
            (tmin,tmax),_,span=render_heatmap(T, inside, origin, h, stride, COLORS, radius_scale=float(self.sz.value()))
            DOC.recompute()
            bb=solid.BoundBox; add_colorbar_legend(bb, COLORS)
            for gp in gates: add_marker(gp, "gate")

            # quick stats
            vox_inside=[(i,j,k) for i in range(nx) for j in range(ny) for k in range(nz) if inside[i][j][k]]
            inside_count=len(vox_inside); thin_count=sum(1 for (i,j,k) in vox_inside if thin_mask[i][j][k])
            thin_pct=(100.0*thin_count/inside_count) if inside_count else 0.0
            times=[T[i][j][k] for (i,j,k) in vox_inside if T[i][j][k]<1e17]
            vis_pts=sum(1 for i in range(0,nx,stride) for j in range(0,ny,stride) for k in range(0,nz,stride) if inside[i][j][k] and T[i][j][k]<1e17)
            # status histogram
            counts=[0]*10
            if times:
                for i in range(nx):
                    for j in range(ny):
                        for k in range(nz):
                            if not inside[i][j][k]: continue
                            tij=T[i][j][k]
                            if tij>1e16: continue
                            nrm=(tij-tmin)/span; b=min(9,int(nrm*9.999)); counts[b]+=1
            early=sum(counts[:2]); mid=sum(counts[2:8]); late=sum(counts[8:]); denom=max(1,sum(counts))
            early_pct=100.0*early/denom; mid_pct=100.0*mid/denom; late_pct=100.0*late/denom

            # welds (skip in fast)
            weld_segs=[]
            if not self.chkFast.isChecked():
                heur=ensure_heuristics()
                weld_segs=extract_weld_lines(T,SRC,inside,origin,h, dt_norm_thresh=heur["weld_dt_threshold"], stride=heur["weld_stride"], max_segments=heur["max_weld_segments"])            
            self._last_maps=(origin,h,dims,inside,None,T,SRC)
            self._last_weld_segs=weld_segs; self._last_gate_points=gates

            # report
            txt=[]
            txt.append(f"Grid: {dims} | cell: {round(h,3)} mm")
            txt.append(f"Overlay points (approx): {vis_pts}")
            txt.append("Legend (arrival time): blue → teal → green → yellow → orange → red (earliest → latest)")
            txt.append(f"Current Mold Flow Status: early {early_pct:.1f}% | mid {mid_pct:.1f}% | late {late_pct:.1f}% of interior volume")
            txt.append(f"Thin-wall: {thin_pct:.1f}% | Weld segs: {len(weld_segs)}")
            txt.append("Suggestions:")
            txt.append("- Move/add gate to shorten longest flow path and balance late-fill zones.")
            txt.append("- Increase mold temp a bit for better knit strength on visible areas; ensure adequate hold/pack.")
            txt.append("- Smooth thickness steps; ribs at 0.5–0.6× wall; add base fillets to cut sink risk.")
            self.out.setPlainText("\n".join(txt))
        except Exception as e:
            self.out.setPlainText(f"Error: {e}")

    def toggle_weld(self):
        if not self._last_maps:
            self.out.append("\nRun 'Show Mold Flow' first."); return
        try:
            if self._last_weld_obj:
                DOC.removeObject(self._last_weld_obj.Name); self._last_weld_obj=None; return
            segs=self._last_weld_segs
            if not segs:
                self.out.append("\nNo weld lines detected with current threshold."); return
            self._last_weld_obj = add_compound_shape(segs, WELD_OBJ_NAME, color=(0.1,0.1,0.1), alpha=0)
        except Exception as e:
            self.out.append(f"\nWeld toggle error: {e}")

    def export_json(self):
        try:
            if not self._last_maps:
                self.out.append("\nRun a flow first."); return
            heur=ensure_heuristics()
            outdir=os.path.join(HEUR_DIR, "exports"); os.makedirs(outdir, exist_ok=True)
            payload={"material": self.cmbMat.currentText(), "gates": self._last_gate_points, "heuristics": heur}
            path=os.path.join(outdir, "moldflow_metrics.json")
            with open(path,"w") as f: json.dump(payload, f, indent=2)
            self.out.append(f"\nExported: {path}")
        except Exception as e:
            self.out.append(f"\nExport error: {e}")


# ------------- Launch -------------
_MFLITE_PANEL=None
def launch():
    global _MFLITE_PANEL
    try:
        _MFLITE_PANEL=MoldFlowLitePanel(); _MFLITE_PANEL.setParent(None)
        _MFLITE_PANEL.setWindowFlags(QtCore.Qt.Window); _MFLITE_PANEL.resize(460, 460); _MFLITE_PANEL.show()
    except Exception as e:
        App.Console.PrintError(f"MoldFlow-Lite launch error: {e}\n")

if __name__=="__main__":
    launch()


# removed corrupted block above and replaced with clean implementation
